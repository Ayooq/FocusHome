--------------------------------------------------------------------------------
-- Generated by NCR Device MIB Maker, Version 01.02.00
-- Generated on 30/06/2008 16:35:31 +0
--------------------------------------------------------------------------------
-- The content of this document is NCR Intellectual Property and is the property
-- of NCR Financial Solutions Group Ltd.  It is to be treated as strictly
-- confidential and is not to be disclosed, reproduced, or used except as
-- authorised in writing by NCR in connection with the manufacture, maintenance,
-- and use of the NCR equipment to which it pertains.
-- Copyright 2004 NCR Financial Solutions Group Ltd.
--------------------------------------------------------------------------------

MON-01-PCMONITOR-MIB DEFINITIONS ::= BEGIN

--------------------------------------------------------------------------------
-- SST mon-01-PcMonitor MIB
--------------------------------------------------------------------------------

IMPORTS
    enterprises, Counter
        FROM RFC1155-SMI
    OBJECT-TYPE
        FROM RFC-1212
    DisplayString
        FROM RFC1213-MIB
    TruthValue
        FROM RFC1253-MIB
    sstDevice, VerificationState, ModuleState, VariableType, ActionType
        FROM NCR-CORESST-MIB;

        mon-01-PcMonitor    OBJECT IDENTIFIER ::= {sstDevice 48 }
        devObjs OBJECT IDENTIFIER ::= {mon-01-PcMonitor 1 }
        srvObjs OBJECT IDENTIFIER ::= {mon-01-PcMonitor 4 }

--------------------------------------------------------------------------------
-- Device Service Miscellaneous Definitions
--------------------------------------------------------------------------------
Reset ::= INTEGER {reset   (1)}


--------------------------------------------------------------------------------
-- SST Device - mon-01-PcMonitor
-------------------------------------------------------------------------------

devManufacturer OBJECT-TYPE
    SYNTAX      DisplayString
    ACCESS      read-only
    STATUS      optional
    DESCRIPTION "The name of the manufacturer of the product."
    ::= {devObjs 1}

devProduct OBJECT-TYPE
    SYNTAX      DisplayString
    ACCESS      read-only
    STATUS      optional
    DESCRIPTION "This attribute does not apply to SST devices."
    ::= {devObjs 2}

devVersion OBJECT-TYPE
    SYNTAX      DisplayString
    ACCESS      read-only
    STATUS      optional
    DESCRIPTION "This attribute does not apply to SST devices."
    ::= {devObjs 3}

devSerialNo OBJECT-TYPE
    SYNTAX      DisplayString
    ACCESS      read-only
    STATUS      optional
    DESCRIPTION "This attribute does not apply to SST devices."
    ::= {devObjs 4}

devInstallation OBJECT-TYPE
    SYNTAX      DisplayString
    ACCESS      read-only
    STATUS      optional
    DESCRIPTION "The date and time, in DMI-defined format, when the component
                 was (last) installed." 
    ::= {devObjs 5}

devVerify OBJECT-TYPE
    SYNTAX      VerificationState
    ACCESS      read-only
    STATUS      optional
    DESCRIPTION "A level of verification that the device software is installed
                 and functioning. This attribute is not currently supported."
    ::= {devObjs 6}

devName OBJECT-TYPE
    SYNTAX      DisplayString
    ACCESS      read-only
    STATUS      mandatory
    DESCRIPTION "The unique, platform-defined name of the device."
    ::= {devObjs 7}

devShortDesc OBJECT-TYPE
    SYNTAX      DisplayString
    ACCESS      read-only
    STATUS      mandatory
    DESCRIPTION "The platform-defined short description of the device."
    ::= {devObjs 8}

devLongDesc OBJECT-TYPE
    SYNTAX      DisplayString
    ACCESS      read-only
    STATUS      mandatory
    DESCRIPTION "The platform-defined long description of the device."
    ::= {devObjs 9}

devUniversalId OBJECT-TYPE
    SYNTAX      INTEGER
    ACCESS      read-only
    STATUS      mandatory
    DESCRIPTION "The unique, platform-defined identifier for the type of
                 device."
    ::= {devObjs 10}

devVariant OBJECT-TYPE
    SYNTAX      INTEGER
    ACCESS      read-only
    STATUS      mandatory
    DESCRIPTION "The identifier for the specific hardware configuration of the
                 device, indicating what hardware the device has."
    ::= {devObjs 11}

devSummaryState OBJECT-TYPE
    SYNTAX      ModuleState
    ACCESS      read-only
    STATUS      mandatory
    DESCRIPTION "The summary state of the device indicating the state of the
                 device's least healthy module."
    ::= {devObjs 12}

-------------------------------------------------------------------------------
-- SST Service Table
-------------------------------------------------------------------------------

srvServiceTable OBJECT-TYPE
    SYNTAX      SEQUENCE OF SrvServiceEntry
    ACCESS      not-accessible
    STATUS      mandatory
    DESCRIPTION "This group defines the attributes of the services associated
                 with the device.."
    ::= {srvObjs 1}

srvServiceEntry OBJECT-TYPE
    SYNTAX      SrvServiceEntry
    ACCESS      not-accessible
    STATUS      mandatory
    DESCRIPTION "This defines the contents of the table."
    INDEX      {srvServiceIndex}
    ::= {srvServiceTable 1}

SrvServiceEntry ::=
    SEQUENCE   {srvServiceIndex           DisplayString,
                srvServiceVariant         INTEGER,
                srvServiceState           OCTET STRING,
                srvServiceMaintenance     OCTET STRING,
                srvServiceReplenishment   OCTET STRING,
                srvServiceClearState      Reset,
                srvServiceClearTallies    Reset}

srvServiceIndex OBJECT-TYPE
    SYNTAX      DisplayString
    ACCESS      read-only
    STATUS      mandatory
    DESCRIPTION "A unique, platform-defined name for each service."
    ::= {srvServiceEntry 1}

srvServiceVariant OBJECT-TYPE
    SYNTAX      INTEGER
    ACCESS      read-only
    STATUS      mandatory
    DESCRIPTION "The current configuration of the service, indicating the
                 additional transaction facilities available to the transaction
                 application."
    ::= {srvServiceEntry 2}

srvServiceState OBJECT-TYPE
    SYNTAX      OCTET STRING
    ACCESS      read-only
    STATUS      mandatory
    DESCRIPTION "This indicates the current level of availability of the
                 service parts to the transaction application."
    ::= {srvServiceEntry 3}

srvServiceMaintenance OBJECT-TYPE
    SYNTAX      OCTET STRING
    ACCESS      read-only
    STATUS      mandatory
    DESCRIPTION "Maintenance information associated with the last state change
                 in the service: M-Code, M-Status and M-Data."
    ::= {srvServiceEntry 4}

srvServiceReplenishment OBJECT-TYPE
    SYNTAX      OCTET STRING
    ACCESS      read-only
    STATUS      mandatory
    DESCRIPTION "Replenishment status data associated with the last state
                 change in the service: RS-Data."
    ::= {srvServiceEntry 5}

srvServiceClearState OBJECT-TYPE
    SYNTAX      Reset
    ACCESS      write-only
    STATUS      mandatory
    DESCRIPTION "Setting the value of this attribute clears all parts of the
                 service to a good (fully functioning and available) state, but
                 does not guarantee that the fault has been cleared."
    ::= {srvServiceEntry 6}

srvServiceClearTallies OBJECT-TYPE
    SYNTAX      Reset
    ACCESS      write-only
    STATUS      mandatory
    DESCRIPTION "Setting the value of this attribute clears all tallies
                 supported by the service."
    ::= {srvServiceEntry 7}
        

-------------------------------------------------------------------------------
-- SST Service Tallies Table
-------------------------------------------------------------------------------

srvServiceTallyTable OBJECT-TYPE
    SYNTAX      SEQUENCE OF SrvServiceTallyEntry
    ACCESS      not-accessible
    STATUS      mandatory
    DESCRIPTION "This group defines the attributes of the counters supported by
                 the device service to record the operations, usage and
                 performance of the device it manages."
    ::= {srvObjs 2}

srvServiceTallyEntry OBJECT-TYPE
    SYNTAX      SrvServiceTallyEntry
    ACCESS      not-accessible
    STATUS      mandatory
    DESCRIPTION "This defines the contents of the table."
    INDEX      {srvServiceNameIndex, 
                srvServiceTallyIndex}
    ::= {srvServiceTallyTable 1}

SrvServiceTallyEntry ::=
    SEQUENCE   {srvServiceNameIndex     DisplayString,
                srvServiceTallyIndex    INTEGER,
                srvServiceTallyName     DisplayString,
                srvServiceTallyValue    Counter}

srvServiceNameIndex OBJECT-TYPE
    SYNTAX      DisplayString
    ACCESS      read-only
    STATUS      mandatory
    DESCRIPTION "A unique name for each service."
    ::= {srvServiceTallyEntry 1}

srvServiceTallyIndex OBJECT-TYPE
    SYNTAX      INTEGER
    ACCESS      read-only
    STATUS      mandatory
    DESCRIPTION "A unique number for each tally."
    ::= {srvServiceTallyEntry 2}

srvServiceTallyName OBJECT-TYPE
    SYNTAX      DisplayString
    ACCESS      read-only
    STATUS      mandatory
    DESCRIPTION "A description of the tally."
    ::= {srvServiceTallyEntry 3}

srvServiceTallyValue OBJECT-TYPE
    SYNTAX      Counter
    ACCESS      read-only
    STATUS      mandatory
    DESCRIPTION "The current value of the tally."
    ::= {srvServiceTallyEntry 4}
END

mon-01-PcMonitor-CONTROLBOARD-MIB DEFINITIONS ::= BEGIN

--
-- SST mon-01-PcMonitor MIB
--

IMPORTS
    enterprises, Counter
        FROM RFC1155-SMI
    OBJECT-TYPE
        FROM RFC-1212
    DisplayString
        FROM RFC1213-MIB
    TruthValue
        FROM RFC1253-MIB
    sstDevice, VerificationState, ModuleState, VariableType, ActionType
        FROM NCR-CORESST-MIB;

    mon-01-PcMonitor    OBJECT IDENTIFIER ::= { sstDevice 48 }
    controlBoard              OBJECT IDENTIFIER ::= { mon-01-PcMonitor 5 }

-------------------------------------------------------------------------------
-- SST Device Module - controlBoard
-----------------------------------------------------------

modIdentifier OBJECT-TYPE
	SYNTAX INTEGER
   ACCESS read-only
   STATUS mandatory
   DESCRIPTION
   "Within the device, this is a unique identifier for the module."
   ::= { controlBoard 1 }

modDesc OBJECT-TYPE
   SYNTAX DisplayString
   ACCESS read-only
   STATUS mandatory
   DESCRIPTION
   "A description of the module."
   ::= { controlBoard 2 }

modReplenishable OBJECT-TYPE
   SYNTAX TruthValue
   ACCESS read-only
   STATUS mandatory
   DESCRIPTION
   "A value of TRUE means the module can be replenished (filled, emptied or renewed).
     A value of FALSE means it can be repaired or replaced."
   ::= { controlBoard 3 }

modCurrentSummaryState OBJECT-TYPE
   SYNTAX ModuleState
   ACCESS read-only
   STATUS mandatory
   DESCRIPTION
   "The current summary state of the module."
   ::= { controlBoard 4 }

modCurrentDetailedState OBJECT-TYPE
   SYNTAX INTEGER
   ACCESS read-only
   STATUS mandatory
   DESCRIPTION
   "The status code for the current detailed state."
   ::= { controlBoard 5 }

modCurrentDetailedStateDesc OBJECT-TYPE
   SYNTAX DisplayString
   ACCESS read-only
   STATUS mandatory
   DESCRIPTION
   "A description of the current detailed state."
   ::= { controlBoard 6 }

modPreviousSummaryState OBJECT-TYPE
   SYNTAX ModuleState
   ACCESS read-only
   STATUS mandatory
   DESCRIPTION
   "The previous summary state of the module."
   ::= { controlBoard 7 }

modPreviousDetailedState OBJECT-TYPE
   SYNTAX INTEGER
   ACCESS read-only
   STATUS mandatory
   DESCRIPTION
   "The status code for the previous detailed state."
   ::= { controlBoard 8 }

modPreviousDetailedStateDesc OBJECT-TYPE
   SYNTAX DisplayString
   ACCESS read-only
   STATUS mandatory
   DESCRIPTION
   "A description of the previous detailed state."
   ::= { controlBoard 9 }

modFaultId OBJECT-TYPE
   SYNTAX DisplayString
   ACCESS read-only
   STATUS mandatory
   DESCRIPTION
   "A string of digits summarizing all the information about the current state of the module."
   ::= { controlBoard 10 }

modAssemSerial OBJECT-TYPE
   SYNTAX DisplayString
   ACCESS read-write
   STATUS optional
   DESCRIPTION
   "The serial number of the module."
   ::= { controlBoard 11 }

modAssemAssem OBJECT-TYPE
   SYNTAX DisplayString
   ACCESS read-write
   STATUS optional
   DESCRIPTION
   "The assembly number of the module."
   ::= { controlBoard 12 }

modAssemCode OBJECT-TYPE
   SYNTAX DisplayString
   ACCESS read-write
   STATUS optional
   DESCRIPTION
   "The manufacturing code of the module."
   ::= { controlBoard 13 }

modPMDate OBJECT-TYPE
   SYNTAX DisplayString
   ACCESS read-write
   STATUS optional
   DESCRIPTION
   "Date of the last scheduled service of the module."
   ::= { controlBoard 14 }

modPMData OBJECT-TYPE
   SYNTAX OCTET STRING
   ACCESS read-write
   STATUS optional
   DESCRIPTION
   "Details of the last scheduled service of the module."
   ::= { controlBoard 15 }

-----------------------------------------------------------
-- Device Module Variable Table - controlBoard
-----------------------------------------------------------

modVarTable OBJECT-TYPE
   SYNTAX  SEQUENCE OF ModVarEntry
   ACCESS  not-accessible
   STATUS  mandatory
   DESCRIPTION
   "This group defines the attributes of the variables used by the module to manage its operational state."
   ::= { controlBoard 16 }

modVarEntry OBJECT-TYPE
    SYNTAX      ModVarEntry
    ACCESS      not-accessible
    STATUS      mandatory
    DESCRIPTION "This defines the contents of the table."
    INDEX      {modVarIndex}
    ::= {modVarTable 1}

ModVarEntry ::=
    SEQUENCE   {modVarIndex         INTEGER,
                modVarDesc          DisplayString,
                modVarType          VariableType,
                modVarValue         Counter,
                modVarThreshold1    INTEGER,
                modVarThreshold2    INTEGER}

modVarIndex OBJECT-TYPE
    SYNTAX      INTEGER
    ACCESS      read-only
    STATUS      mandatory
    DESCRIPTION "This is a unique number for every entry in the module 
                 variables table."
    ::= {modVarEntry 1}

modVarDesc OBJECT-TYPE
    SYNTAX      DisplayString
    ACCESS      read-only
    STATUS      mandatory
    DESCRIPTION "A description of the module variable."
    ::= {modVarEntry 2}

modVarType OBJECT-TYPE
    SYNTAX      VariableType
    ACCESS      read-only
    STATUS      mandatory
    DESCRIPTION "An enumerated value indicating whether the variable has
                 thresholds and the type of threshold."
    ::= {modVarEntry 3}

modVarValue OBJECT-TYPE
    SYNTAX      Counter
    ACCESS      read-only
    STATUS      mandatory
    DESCRIPTION "The value of the module variable."
    ::= {modVarEntry 4}

modVarThreshold1 OBJECT-TYPE
    SYNTAX      INTEGER
    ACCESS      read-write
    STATUS      optional
    DESCRIPTION "For variables with one threshold, this is a final value.
                 For variables with two thresholds, this is a warning value."
    ::= {modVarEntry 5}

modVarThreshold2 OBJECT-TYPE
    SYNTAX      INTEGER
    ACCESS      read-write
    STATUS      optional
    DESCRIPTION "For variables with two thresholds, this is the final value."
    ::= {modVarEntry 6}

-------------------------------------------------------------------------------
-- Device Module Actions Table - controlBoard
-----------------------------------------------------------

modActionTable OBJECT-TYPE
   SYNTAX  SEQUENCE OF ModActionEntry
   ACCESS  not-accessible
   STATUS  mandatory
   DESCRIPTION
   "This group defines the attributes of the actions that can be performed on the module to restore or maintain its normal operational state."
   ::= { controlBoard 17 }

modActionEntry OBJECT-TYPE
    SYNTAX      ModActionEntry
    ACCESS      not-accessible
    STATUS      mandatory
    DESCRIPTION "This defines the contents of the table."
    INDEX      {modActionIndex}
    ::= {modActionTable 1}

ModActionEntry ::=
    SEQUENCE   {modActionIndex               INTEGER,
                modActionDesc                DisplayString,
                modActionType                ActionType,
                modActionFaultDetect         TruthValue,
                modActionProactive           TruthValue,
                modActionProactiveDetect     TruthValue,
                modActionCustomerActionable  TruthValue,
                modActionComplete            TruthValue}

modActionIndex OBJECT-TYPE
    SYNTAX      INTEGER
    ACCESS      read-only
    STATUS      mandatory
    DESCRIPTION "A unique number for each action in the module actions table."
    ::= {modActionEntry 1}

modActionDesc OBJECT-TYPE
    SYNTAX      DisplayString
    ACCESS      read-only
    STATUS      mandatory
    DESCRIPTION "A description of the module action."
    ::= {modActionEntry 2}

modActionType OBJECT-TYPE
    SYNTAX      ActionType
    ACCESS      read-only
    STATUS      mandatory
    DESCRIPTION "An enumerated value indicating the type of action performed on
                 the module."
    ::= {modActionEntry 3}

modActionFaultDetect OBJECT-TYPE
    SYNTAX      TruthValue
    ACCESS      read-only
    STATUS      mandatory
    DESCRIPTION "A value of TRUE means the module can automatically detect that
                 the action has been performed for the associated fault that
                 was reported."
    ::= {modActionEntry 4}

modActionProactive OBJECT-TYPE
    SYNTAX      TruthValue
    ACCESS      read-only
    STATUS      mandatory
    DESCRIPTION "A value of TRUE means the action can be performed on the
                 module before the associated fault occurs."
    ::= {modActionEntry 5}

modActionProactiveDetect OBJECT-TYPE
    SYNTAX      TruthValue
    ACCESS      read-only
    STATUS      mandatory
    DESCRIPTION "A value of TRUE means the module can, through its sensors,
                 automatically detect that the action has been performed before
                 the associated fault occurs."
    ::= {modActionEntry 6}

modActionCustomerActionable OBJECT-TYPE
    SYNTAX      TruthValue
    ACCESS      read-only
    STATUS      mandatory
    DESCRIPTION "A value of TRUE means the customer can perform the action."
    ::= {modActionEntry 7}

modActionComplete OBJECT-TYPE
    SYNTAX      TruthValue
    ACCESS      write-only
    STATUS      mandatory
    DESCRIPTION "Setting the value of this attribute to TRUE informs the module
                 that the action has been performed, and clears the appropriate
                 module variables."
    ::= {modActionEntry 8}

END
