--------------------------------------------------------------------------------
-- Generated by NCR Device MIB Maker, Version 01.02.00
-- Generated on 12/12/2006 14:49:51 +0
--------------------------------------------------------------------------------
-- The content of this document is NCR Intellectual Property and is the property
-- of NCR Financial Solutions Group Ltd.  It is to be treated as strictly
-- confidential and is not to be disclosed, reproduced, or used except as
-- authorised in writing by NCR in connection with the manufacture, maintenance,
-- and use of the NCR equipment to which it pertains.
-- Copyright 2004 NCR Financial Solutions Group Ltd.
--------------------------------------------------------------------------------

CASH-01-USBDISPENSER-MIB DEFINITIONS ::= BEGIN

--------------------------------------------------------------------------------
-- SST CASH-01-USBDISPENSER MIB
--------------------------------------------------------------------------------

IMPORTS
    enterprises, Counter
        FROM RFC1155-SMI
    OBJECT-TYPE
        FROM RFC-1212
    DisplayString
        FROM RFC1213-MIB
    TruthValue
        FROM RFC1253-MIB
    sstDevice, VerificationState, ModuleState, VariableType, ActionType
        FROM NCR-CORESST-MIB;

        cash-01-UsbDispenser    OBJECT IDENTIFIER ::= {sstDevice 155 }
        devObjs OBJECT IDENTIFIER ::= {cash-01-UsbDispenser 1 }
        srvObjs OBJECT IDENTIFIER ::= {cash-01-UsbDispenser 4 }

--------------------------------------------------------------------------------
-- Device Service Miscellaneous Definitions
--------------------------------------------------------------------------------
Reset ::= INTEGER {reset   (1)}


--------------------------------------------------------------------------------
-- SST Device - CASH-01-UsbDispenser
-------------------------------------------------------------------------------

devManufacturer OBJECT-TYPE
    SYNTAX      DisplayString
    ACCESS      read-only
    STATUS      optional
    DESCRIPTION "The name of the manufacturer of the product."
    ::= {devObjs 1}

devProduct OBJECT-TYPE
    SYNTAX      DisplayString
    ACCESS      read-only
    STATUS      optional
    DESCRIPTION "This attribute does not apply to SST devices."
    ::= {devObjs 2}

devVersion OBJECT-TYPE
    SYNTAX      DisplayString
    ACCESS      read-only
    STATUS      optional
    DESCRIPTION "This attribute does not apply to SST devices."
    ::= {devObjs 3}

devSerialNo OBJECT-TYPE
    SYNTAX      DisplayString
    ACCESS      read-only
    STATUS      optional
    DESCRIPTION "This attribute does not apply to SST devices."
    ::= {devObjs 4}

devInstallation OBJECT-TYPE
    SYNTAX      DisplayString
    ACCESS      read-only
    STATUS      optional
    DESCRIPTION "The date and time, in DMI-defined format, when the component
                 was (last) installed." 
    ::= {devObjs 5}

devVerify OBJECT-TYPE
    SYNTAX      VerificationState
    ACCESS      read-only
    STATUS      optional
    DESCRIPTION "A level of verification that the device software is installed
                 and functioning. This attribute is not currently supported."
    ::= {devObjs 6}

devName OBJECT-TYPE
    SYNTAX      DisplayString
    ACCESS      read-only
    STATUS      mandatory
    DESCRIPTION "The unique, platform-defined name of the device."
    ::= {devObjs 7}

devShortDesc OBJECT-TYPE
    SYNTAX      DisplayString
    ACCESS      read-only
    STATUS      mandatory
    DESCRIPTION "The platform-defined short description of the device."
    ::= {devObjs 8}

devLongDesc OBJECT-TYPE
    SYNTAX      DisplayString
    ACCESS      read-only
    STATUS      mandatory
    DESCRIPTION "The platform-defined long description of the device."
    ::= {devObjs 9}

devUniversalId OBJECT-TYPE
    SYNTAX      INTEGER
    ACCESS      read-only
    STATUS      mandatory
    DESCRIPTION "The unique, platform-defined identifier for the type of
                 device."
    ::= {devObjs 10}

devVariant OBJECT-TYPE
    SYNTAX      INTEGER
    ACCESS      read-only
    STATUS      mandatory
    DESCRIPTION "The identifier for the specific hardware configuration of the
                 device, indicating what hardware the device has."
    ::= {devObjs 11}

devSummaryState OBJECT-TYPE
    SYNTAX      ModuleState
    ACCESS      read-only
    STATUS      mandatory
    DESCRIPTION "The summary state of the device indicating the state of the
                 device's least healthy module."
    ::= {devObjs 12}

-------------------------------------------------------------------------------
-- SST Service Table
-------------------------------------------------------------------------------

srvServiceTable OBJECT-TYPE
    SYNTAX      SEQUENCE OF SrvServiceEntry
    ACCESS      not-accessible
    STATUS      mandatory
    DESCRIPTION "This group defines the attributes of the services associated
                 with the device.."
    ::= {srvObjs 1}

srvServiceEntry OBJECT-TYPE
    SYNTAX      SrvServiceEntry
    ACCESS      not-accessible
    STATUS      mandatory
    DESCRIPTION "This defines the contents of the table."
    INDEX      {srvServiceIndex}
    ::= {srvServiceTable 1}

SrvServiceEntry ::=
    SEQUENCE   {srvServiceIndex           DisplayString,
                srvServiceVariant         INTEGER,
                srvServiceState           OCTET STRING,
                srvServiceMaintenance     OCTET STRING,
                srvServiceReplenishment   OCTET STRING,
                srvServiceClearState      Reset,
                srvServiceClearTallies    Reset}

srvServiceIndex OBJECT-TYPE
    SYNTAX      DisplayString
    ACCESS      read-only
    STATUS      mandatory
    DESCRIPTION "A unique, platform-defined name for each service."
    ::= {srvServiceEntry 1}

srvServiceVariant OBJECT-TYPE
    SYNTAX      INTEGER
    ACCESS      read-only
    STATUS      mandatory
    DESCRIPTION "The current configuration of the service, indicating the
                 additional transaction facilities available to the transaction
                 application."
    ::= {srvServiceEntry 2}

srvServiceState OBJECT-TYPE
    SYNTAX      OCTET STRING
    ACCESS      read-only
    STATUS      mandatory
    DESCRIPTION "This indicates the current level of availability of the
                 service parts to the transaction application."
    ::= {srvServiceEntry 3}

srvServiceMaintenance OBJECT-TYPE
    SYNTAX      OCTET STRING
    ACCESS      read-only
    STATUS      mandatory
    DESCRIPTION "Maintenance information associated with the last state change
                 in the service: M-Code, M-Status and M-Data."
    ::= {srvServiceEntry 4}

srvServiceReplenishment OBJECT-TYPE
    SYNTAX      OCTET STRING
    ACCESS      read-only
    STATUS      mandatory
    DESCRIPTION "Replenishment status data associated with the last state
                 change in the service: RS-Data."
    ::= {srvServiceEntry 5}

srvServiceClearState OBJECT-TYPE
    SYNTAX      Reset
    ACCESS      write-only
    STATUS      mandatory
    DESCRIPTION "Setting the value of this attribute clears all parts of the
                 service to a good (fully functioning and available) state, but
                 does not guarantee that the fault has been cleared."
    ::= {srvServiceEntry 6}

srvServiceClearTallies OBJECT-TYPE
    SYNTAX      Reset
    ACCESS      write-only
    STATUS      mandatory
    DESCRIPTION "Setting the value of this attribute clears all tallies
                 supported by the service."
    ::= {srvServiceEntry 7}
        

-------------------------------------------------------------------------------
-- SST Service Tallies Table
-------------------------------------------------------------------------------

srvServiceTallyTable OBJECT-TYPE
    SYNTAX      SEQUENCE OF SrvServiceTallyEntry
    ACCESS      not-accessible
    STATUS      mandatory
    DESCRIPTION "This group defines the attributes of the counters supported by
                 the device service to record the operations, usage and
                 performance of the device it manages."
    ::= {srvObjs 2}

srvServiceTallyEntry OBJECT-TYPE
    SYNTAX      SrvServiceTallyEntry
    ACCESS      not-accessible
    STATUS      mandatory
    DESCRIPTION "This defines the contents of the table."
    INDEX      {srvServiceNameIndex, 
                srvServiceTallyIndex}
    ::= {srvServiceTallyTable 1}

SrvServiceTallyEntry ::=
    SEQUENCE   {srvServiceNameIndex     DisplayString,
                srvServiceTallyIndex    INTEGER,
                srvServiceTallyName     DisplayString,
                srvServiceTallyValue    Counter}

srvServiceNameIndex OBJECT-TYPE
    SYNTAX      DisplayString
    ACCESS      read-only
    STATUS      mandatory
    DESCRIPTION "A unique name for each service."
    ::= {srvServiceTallyEntry 1}

srvServiceTallyIndex OBJECT-TYPE
    SYNTAX      INTEGER
    ACCESS      read-only
    STATUS      mandatory
    DESCRIPTION "A unique number for each tally."
    ::= {srvServiceTallyEntry 2}

srvServiceTallyName OBJECT-TYPE
    SYNTAX      DisplayString
    ACCESS      read-only
    STATUS      mandatory
    DESCRIPTION "A description of the tally."
    ::= {srvServiceTallyEntry 3}

srvServiceTallyValue OBJECT-TYPE
    SYNTAX      Counter
    ACCESS      read-only
    STATUS      mandatory
    DESCRIPTION "The current value of the tally."
    ::= {srvServiceTallyEntry 4}
END

CASH-01-USBDISPENSER-CONTROLBOARD-MIB DEFINITIONS ::= BEGIN

--
-- SST CASH-01-USBDISPENSER MIB
--

IMPORTS
    enterprises, Counter
        FROM RFC1155-SMI
    OBJECT-TYPE
        FROM RFC-1212
    DisplayString
        FROM RFC1213-MIB
    TruthValue
        FROM RFC1253-MIB
    sstDevice, VerificationState, ModuleState, VariableType, ActionType
        FROM NCR-CORESST-MIB;

    cash-01-UsbDispenser    OBJECT IDENTIFIER ::= { sstDevice 155 }
    controlBoard              OBJECT IDENTIFIER ::= { cash-01-UsbDispenser 5 }

-------------------------------------------------------------------------------
-- SST Device Module - controlBoard
-----------------------------------------------------------

modIdentifier OBJECT-TYPE
	SYNTAX INTEGER
   ACCESS read-only
   STATUS mandatory
   DESCRIPTION
   "Within the device, this is a unique identifier for the module."
   ::= { controlBoard 1 }

modDesc OBJECT-TYPE
   SYNTAX DisplayString
   ACCESS read-only
   STATUS mandatory
   DESCRIPTION
   "A description of the module."
   ::= { controlBoard 2 }

modReplenishable OBJECT-TYPE
   SYNTAX TruthValue
   ACCESS read-only
   STATUS mandatory
   DESCRIPTION
   "A value of TRUE means the module can be replenished (filled, emptied or renewed).
     A value of FALSE means it can be repaired or replaced."
   ::= { controlBoard 3 }

modCurrentSummaryState OBJECT-TYPE
   SYNTAX ModuleState
   ACCESS read-only
   STATUS mandatory
   DESCRIPTION
   "The current summary state of the module."
   ::= { controlBoard 4 }

modCurrentDetailedState OBJECT-TYPE
   SYNTAX INTEGER
   ACCESS read-only
   STATUS mandatory
   DESCRIPTION
   "The status code for the current detailed state."
   ::= { controlBoard 5 }

modCurrentDetailedStateDesc OBJECT-TYPE
   SYNTAX DisplayString
   ACCESS read-only
   STATUS mandatory
   DESCRIPTION
   "A description of the current detailed state."
   ::= { controlBoard 6 }

modPreviousSummaryState OBJECT-TYPE
   SYNTAX ModuleState
   ACCESS read-only
   STATUS mandatory
   DESCRIPTION
   "The previous summary state of the module."
   ::= { controlBoard 7 }

modPreviousDetailedState OBJECT-TYPE
   SYNTAX INTEGER
   ACCESS read-only
   STATUS mandatory
   DESCRIPTION
   "The status code for the previous detailed state."
   ::= { controlBoard 8 }

modPreviousDetailedStateDesc OBJECT-TYPE
   SYNTAX DisplayString
   ACCESS read-only
   STATUS mandatory
   DESCRIPTION
   "A description of the previous detailed state."
   ::= { controlBoard 9 }

modFaultId OBJECT-TYPE
   SYNTAX DisplayString
   ACCESS read-only
   STATUS mandatory
   DESCRIPTION
   "A string of digits summarizing all the information about the current state of the module."
   ::= { controlBoard 10 }

modAssemSerial OBJECT-TYPE
   SYNTAX DisplayString
   ACCESS read-write
   STATUS optional
   DESCRIPTION
   "The serial number of the module."
   ::= { controlBoard 11 }

modAssemAssem OBJECT-TYPE
   SYNTAX DisplayString
   ACCESS read-write
   STATUS optional
   DESCRIPTION
   "The assembly number of the module."
   ::= { controlBoard 12 }

modAssemCode OBJECT-TYPE
   SYNTAX DisplayString
   ACCESS read-write
   STATUS optional
   DESCRIPTION
   "The manufacturing code of the module."
   ::= { controlBoard 13 }

modPMDate OBJECT-TYPE
   SYNTAX DisplayString
   ACCESS read-write
   STATUS optional
   DESCRIPTION
   "Date of the last scheduled service of the module."
   ::= { controlBoard 14 }

modPMData OBJECT-TYPE
   SYNTAX OCTET STRING
   ACCESS read-write
   STATUS optional
   DESCRIPTION
   "Details of the last scheduled service of the module."
   ::= { controlBoard 15 }

-----------------------------------------------------------
-- Device Module Variable Table - controlBoard
-----------------------------------------------------------

modVarTable OBJECT-TYPE
   SYNTAX  SEQUENCE OF ModVarEntry
   ACCESS  not-accessible
   STATUS  mandatory
   DESCRIPTION
   "This group defines the attributes of the variables used by the module to manage its operational state."
   ::= { controlBoard 16 }

modVarEntry OBJECT-TYPE
    SYNTAX      ModVarEntry
    ACCESS      not-accessible
    STATUS      mandatory
    DESCRIPTION "This defines the contents of the table."
    INDEX      {modVarIndex}
    ::= {modVarTable 1}

ModVarEntry ::=
    SEQUENCE   {modVarIndex         INTEGER,
                modVarDesc          DisplayString,
                modVarType          VariableType,
                modVarValue         Counter,
                modVarThreshold1    INTEGER,
                modVarThreshold2    INTEGER}

modVarIndex OBJECT-TYPE
    SYNTAX      INTEGER
    ACCESS      read-only
    STATUS      mandatory
    DESCRIPTION "This is a unique number for every entry in the module 
                 variables table."
    ::= {modVarEntry 1}

modVarDesc OBJECT-TYPE
    SYNTAX      DisplayString
    ACCESS      read-only
    STATUS      mandatory
    DESCRIPTION "A description of the module variable."
    ::= {modVarEntry 2}

modVarType OBJECT-TYPE
    SYNTAX      VariableType
    ACCESS      read-only
    STATUS      mandatory
    DESCRIPTION "An enumerated value indicating whether the variable has
                 thresholds and the type of threshold."
    ::= {modVarEntry 3}

modVarValue OBJECT-TYPE
    SYNTAX      Counter
    ACCESS      read-only
    STATUS      mandatory
    DESCRIPTION "The value of the module variable."
    ::= {modVarEntry 4}

modVarThreshold1 OBJECT-TYPE
    SYNTAX      INTEGER
    ACCESS      read-write
    STATUS      optional
    DESCRIPTION "For variables with one threshold, this is a final value.
                 For variables with two thresholds, this is a warning value."
    ::= {modVarEntry 5}

modVarThreshold2 OBJECT-TYPE
    SYNTAX      INTEGER
    ACCESS      read-write
    STATUS      optional
    DESCRIPTION "For variables with two thresholds, this is the final value."
    ::= {modVarEntry 6}

-------------------------------------------------------------------------------
-- Device Module Actions Table - controlBoard
-----------------------------------------------------------

modActionTable OBJECT-TYPE
   SYNTAX  SEQUENCE OF ModActionEntry
   ACCESS  not-accessible
   STATUS  mandatory
   DESCRIPTION
   "This group defines the attributes of the actions that can be performed on the module to restore or maintain its normal operational state."
   ::= { controlBoard 17 }

modActionEntry OBJECT-TYPE
    SYNTAX      ModActionEntry
    ACCESS      not-accessible
    STATUS      mandatory
    DESCRIPTION "This defines the contents of the table."
    INDEX      {modActionIndex}
    ::= {modActionTable 1}

ModActionEntry ::=
    SEQUENCE   {modActionIndex               INTEGER,
                modActionDesc                DisplayString,
                modActionType                ActionType,
                modActionFaultDetect         TruthValue,
                modActionProactive           TruthValue,
                modActionProactiveDetect     TruthValue,
                modActionCustomerActionable  TruthValue,
                modActionComplete            TruthValue}

modActionIndex OBJECT-TYPE
    SYNTAX      INTEGER
    ACCESS      read-only
    STATUS      mandatory
    DESCRIPTION "A unique number for each action in the module actions table."
    ::= {modActionEntry 1}

modActionDesc OBJECT-TYPE
    SYNTAX      DisplayString
    ACCESS      read-only
    STATUS      mandatory
    DESCRIPTION "A description of the module action."
    ::= {modActionEntry 2}

modActionType OBJECT-TYPE
    SYNTAX      ActionType
    ACCESS      read-only
    STATUS      mandatory
    DESCRIPTION "An enumerated value indicating the type of action performed on
                 the module."
    ::= {modActionEntry 3}

modActionFaultDetect OBJECT-TYPE
    SYNTAX      TruthValue
    ACCESS      read-only
    STATUS      mandatory
    DESCRIPTION "A value of TRUE means the module can automatically detect that
                 the action has been performed for the associated fault that
                 was reported."
    ::= {modActionEntry 4}

modActionProactive OBJECT-TYPE
    SYNTAX      TruthValue
    ACCESS      read-only
    STATUS      mandatory
    DESCRIPTION "A value of TRUE means the action can be performed on the
                 module before the associated fault occurs."
    ::= {modActionEntry 5}

modActionProactiveDetect OBJECT-TYPE
    SYNTAX      TruthValue
    ACCESS      read-only
    STATUS      mandatory
    DESCRIPTION "A value of TRUE means the module can, through its sensors,
                 automatically detect that the action has been performed before
                 the associated fault occurs."
    ::= {modActionEntry 6}

modActionCustomerActionable OBJECT-TYPE
    SYNTAX      TruthValue
    ACCESS      read-only
    STATUS      mandatory
    DESCRIPTION "A value of TRUE means the customer can perform the action."
    ::= {modActionEntry 7}

modActionComplete OBJECT-TYPE
    SYNTAX      TruthValue
    ACCESS      write-only
    STATUS      mandatory
    DESCRIPTION "Setting the value of this attribute to TRUE informs the module
                 that the action has been performed, and clears the appropriate
                 module variables."
    ::= {modActionEntry 8}

END

CASH-01-USBDISPENSER-TOPPICKMODULE-MIB DEFINITIONS ::= BEGIN

--
-- SST CASH-01-USBDISPENSER MIB
--

IMPORTS
    enterprises, Counter
        FROM RFC1155-SMI
    OBJECT-TYPE
        FROM RFC-1212
    DisplayString
        FROM RFC1213-MIB
    TruthValue
        FROM RFC1253-MIB
    sstDevice, VerificationState, ModuleState, VariableType, ActionType
        FROM NCR-CORESST-MIB;

    cash-01-UsbDispenser    OBJECT IDENTIFIER ::= { sstDevice 155 }
    topPickModule              OBJECT IDENTIFIER ::= { cash-01-UsbDispenser 6 }

-------------------------------------------------------------------------------
-- SST Device Module - topPickModule
-----------------------------------------------------------

modIdentifier OBJECT-TYPE
	SYNTAX INTEGER
   ACCESS read-only
   STATUS mandatory
   DESCRIPTION
   "Within the device, this is a unique identifier for the module."
   ::= { topPickModule 1 }

modDesc OBJECT-TYPE
   SYNTAX DisplayString
   ACCESS read-only
   STATUS mandatory
   DESCRIPTION
   "A description of the module."
   ::= { topPickModule 2 }

modReplenishable OBJECT-TYPE
   SYNTAX TruthValue
   ACCESS read-only
   STATUS mandatory
   DESCRIPTION
   "A value of TRUE means the module can be replenished (filled, emptied or renewed).
     A value of FALSE means it can be repaired or replaced."
   ::= { topPickModule 3 }

modCurrentSummaryState OBJECT-TYPE
   SYNTAX ModuleState
   ACCESS read-only
   STATUS mandatory
   DESCRIPTION
   "The current summary state of the module."
   ::= { topPickModule 4 }

modCurrentDetailedState OBJECT-TYPE
   SYNTAX INTEGER
   ACCESS read-only
   STATUS mandatory
   DESCRIPTION
   "The status code for the current detailed state."
   ::= { topPickModule 5 }

modCurrentDetailedStateDesc OBJECT-TYPE
   SYNTAX DisplayString
   ACCESS read-only
   STATUS mandatory
   DESCRIPTION
   "A description of the current detailed state."
   ::= { topPickModule 6 }

modPreviousSummaryState OBJECT-TYPE
   SYNTAX ModuleState
   ACCESS read-only
   STATUS mandatory
   DESCRIPTION
   "The previous summary state of the module."
   ::= { topPickModule 7 }

modPreviousDetailedState OBJECT-TYPE
   SYNTAX INTEGER
   ACCESS read-only
   STATUS mandatory
   DESCRIPTION
   "The status code for the previous detailed state."
   ::= { topPickModule 8 }

modPreviousDetailedStateDesc OBJECT-TYPE
   SYNTAX DisplayString
   ACCESS read-only
   STATUS mandatory
   DESCRIPTION
   "A description of the previous detailed state."
   ::= { topPickModule 9 }

modFaultId OBJECT-TYPE
   SYNTAX DisplayString
   ACCESS read-only
   STATUS mandatory
   DESCRIPTION
   "A string of digits summarizing all the information about the current state of the module."
   ::= { topPickModule 10 }

modAssemSerial OBJECT-TYPE
   SYNTAX DisplayString
   ACCESS read-write
   STATUS optional
   DESCRIPTION
   "The serial number of the module."
   ::= { topPickModule 11 }

modAssemAssem OBJECT-TYPE
   SYNTAX DisplayString
   ACCESS read-write
   STATUS optional
   DESCRIPTION
   "The assembly number of the module."
   ::= { topPickModule 12 }

modAssemCode OBJECT-TYPE
   SYNTAX DisplayString
   ACCESS read-write
   STATUS optional
   DESCRIPTION
   "The manufacturing code of the module."
   ::= { topPickModule 13 }

modPMDate OBJECT-TYPE
   SYNTAX DisplayString
   ACCESS read-write
   STATUS optional
   DESCRIPTION
   "Date of the last scheduled service of the module."
   ::= { topPickModule 14 }

modPMData OBJECT-TYPE
   SYNTAX OCTET STRING
   ACCESS read-write
   STATUS optional
   DESCRIPTION
   "Details of the last scheduled service of the module."
   ::= { topPickModule 15 }

-----------------------------------------------------------
-- Device Module Variable Table - topPickModule
-----------------------------------------------------------

modVarTable OBJECT-TYPE
   SYNTAX  SEQUENCE OF ModVarEntry
   ACCESS  not-accessible
   STATUS  mandatory
   DESCRIPTION
   "This group defines the attributes of the variables used by the module to manage its operational state."
   ::= { topPickModule 16 }

modVarEntry OBJECT-TYPE
    SYNTAX      ModVarEntry
    ACCESS      not-accessible
    STATUS      mandatory
    DESCRIPTION "This defines the contents of the table."
    INDEX      {modVarIndex}
    ::= {modVarTable 1}

ModVarEntry ::=
    SEQUENCE   {modVarIndex         INTEGER,
                modVarDesc          DisplayString,
                modVarType          VariableType,
                modVarValue         Counter,
                modVarThreshold1    INTEGER,
                modVarThreshold2    INTEGER}

modVarIndex OBJECT-TYPE
    SYNTAX      INTEGER
    ACCESS      read-only
    STATUS      mandatory
    DESCRIPTION "This is a unique number for every entry in the module 
                 variables table."
    ::= {modVarEntry 1}

modVarDesc OBJECT-TYPE
    SYNTAX      DisplayString
    ACCESS      read-only
    STATUS      mandatory
    DESCRIPTION "A description of the module variable."
    ::= {modVarEntry 2}

modVarType OBJECT-TYPE
    SYNTAX      VariableType
    ACCESS      read-only
    STATUS      mandatory
    DESCRIPTION "An enumerated value indicating whether the variable has
                 thresholds and the type of threshold."
    ::= {modVarEntry 3}

modVarValue OBJECT-TYPE
    SYNTAX      Counter
    ACCESS      read-only
    STATUS      mandatory
    DESCRIPTION "The value of the module variable."
    ::= {modVarEntry 4}

modVarThreshold1 OBJECT-TYPE
    SYNTAX      INTEGER
    ACCESS      read-write
    STATUS      optional
    DESCRIPTION "For variables with one threshold, this is a final value.
                 For variables with two thresholds, this is a warning value."
    ::= {modVarEntry 5}

modVarThreshold2 OBJECT-TYPE
    SYNTAX      INTEGER
    ACCESS      read-write
    STATUS      optional
    DESCRIPTION "For variables with two thresholds, this is the final value."
    ::= {modVarEntry 6}

-------------------------------------------------------------------------------
-- Device Module Actions Table - topPickModule
-----------------------------------------------------------

modActionTable OBJECT-TYPE
   SYNTAX  SEQUENCE OF ModActionEntry
   ACCESS  not-accessible
   STATUS  mandatory
   DESCRIPTION
   "This group defines the attributes of the actions that can be performed on the module to restore or maintain its normal operational state."
   ::= { topPickModule 17 }

modActionEntry OBJECT-TYPE
    SYNTAX      ModActionEntry
    ACCESS      not-accessible
    STATUS      mandatory
    DESCRIPTION "This defines the contents of the table."
    INDEX      {modActionIndex}
    ::= {modActionTable 1}

ModActionEntry ::=
    SEQUENCE   {modActionIndex               INTEGER,
                modActionDesc                DisplayString,
                modActionType                ActionType,
                modActionFaultDetect         TruthValue,
                modActionProactive           TruthValue,
                modActionProactiveDetect     TruthValue,
                modActionCustomerActionable  TruthValue,
                modActionComplete            TruthValue}

modActionIndex OBJECT-TYPE
    SYNTAX      INTEGER
    ACCESS      read-only
    STATUS      mandatory
    DESCRIPTION "A unique number for each action in the module actions table."
    ::= {modActionEntry 1}

modActionDesc OBJECT-TYPE
    SYNTAX      DisplayString
    ACCESS      read-only
    STATUS      mandatory
    DESCRIPTION "A description of the module action."
    ::= {modActionEntry 2}

modActionType OBJECT-TYPE
    SYNTAX      ActionType
    ACCESS      read-only
    STATUS      mandatory
    DESCRIPTION "An enumerated value indicating the type of action performed on
                 the module."
    ::= {modActionEntry 3}

modActionFaultDetect OBJECT-TYPE
    SYNTAX      TruthValue
    ACCESS      read-only
    STATUS      mandatory
    DESCRIPTION "A value of TRUE means the module can automatically detect that
                 the action has been performed for the associated fault that
                 was reported."
    ::= {modActionEntry 4}

modActionProactive OBJECT-TYPE
    SYNTAX      TruthValue
    ACCESS      read-only
    STATUS      mandatory
    DESCRIPTION "A value of TRUE means the action can be performed on the
                 module before the associated fault occurs."
    ::= {modActionEntry 5}

modActionProactiveDetect OBJECT-TYPE
    SYNTAX      TruthValue
    ACCESS      read-only
    STATUS      mandatory
    DESCRIPTION "A value of TRUE means the module can, through its sensors,
                 automatically detect that the action has been performed before
                 the associated fault occurs."
    ::= {modActionEntry 6}

modActionCustomerActionable OBJECT-TYPE
    SYNTAX      TruthValue
    ACCESS      read-only
    STATUS      mandatory
    DESCRIPTION "A value of TRUE means the customer can perform the action."
    ::= {modActionEntry 7}

modActionComplete OBJECT-TYPE
    SYNTAX      TruthValue
    ACCESS      write-only
    STATUS      mandatory
    DESCRIPTION "Setting the value of this attribute to TRUE informs the module
                 that the action has been performed, and clears the appropriate
                 module variables."
    ::= {modActionEntry 8}

END

CASH-01-USBDISPENSER-SECONDPICKMODULE-MIB DEFINITIONS ::= BEGIN

--
-- SST CASH-01-USBDISPENSER MIB
--

IMPORTS
    enterprises, Counter
        FROM RFC1155-SMI
    OBJECT-TYPE
        FROM RFC-1212
    DisplayString
        FROM RFC1213-MIB
    TruthValue
        FROM RFC1253-MIB
    sstDevice, VerificationState, ModuleState, VariableType, ActionType
        FROM NCR-CORESST-MIB;

    cash-01-UsbDispenser    OBJECT IDENTIFIER ::= { sstDevice 155 }
    secondPickModule              OBJECT IDENTIFIER ::= { cash-01-UsbDispenser 7 }

-------------------------------------------------------------------------------
-- SST Device Module - secondPickModule
-----------------------------------------------------------

modIdentifier OBJECT-TYPE
	SYNTAX INTEGER
   ACCESS read-only
   STATUS mandatory
   DESCRIPTION
   "Within the device, this is a unique identifier for the module."
   ::= { secondPickModule 1 }

modDesc OBJECT-TYPE
   SYNTAX DisplayString
   ACCESS read-only
   STATUS mandatory
   DESCRIPTION
   "A description of the module."
   ::= { secondPickModule 2 }

modReplenishable OBJECT-TYPE
   SYNTAX TruthValue
   ACCESS read-only
   STATUS mandatory
   DESCRIPTION
   "A value of TRUE means the module can be replenished (filled, emptied or renewed).
     A value of FALSE means it can be repaired or replaced."
   ::= { secondPickModule 3 }

modCurrentSummaryState OBJECT-TYPE
   SYNTAX ModuleState
   ACCESS read-only
   STATUS mandatory
   DESCRIPTION
   "The current summary state of the module."
   ::= { secondPickModule 4 }

modCurrentDetailedState OBJECT-TYPE
   SYNTAX INTEGER
   ACCESS read-only
   STATUS mandatory
   DESCRIPTION
   "The status code for the current detailed state."
   ::= { secondPickModule 5 }

modCurrentDetailedStateDesc OBJECT-TYPE
   SYNTAX DisplayString
   ACCESS read-only
   STATUS mandatory
   DESCRIPTION
   "A description of the current detailed state."
   ::= { secondPickModule 6 }

modPreviousSummaryState OBJECT-TYPE
   SYNTAX ModuleState
   ACCESS read-only
   STATUS mandatory
   DESCRIPTION
   "The previous summary state of the module."
   ::= { secondPickModule 7 }

modPreviousDetailedState OBJECT-TYPE
   SYNTAX INTEGER
   ACCESS read-only
   STATUS mandatory
   DESCRIPTION
   "The status code for the previous detailed state."
   ::= { secondPickModule 8 }

modPreviousDetailedStateDesc OBJECT-TYPE
   SYNTAX DisplayString
   ACCESS read-only
   STATUS mandatory
   DESCRIPTION
   "A description of the previous detailed state."
   ::= { secondPickModule 9 }

modFaultId OBJECT-TYPE
   SYNTAX DisplayString
   ACCESS read-only
   STATUS mandatory
   DESCRIPTION
   "A string of digits summarizing all the information about the current state of the module."
   ::= { secondPickModule 10 }

modAssemSerial OBJECT-TYPE
   SYNTAX DisplayString
   ACCESS read-write
   STATUS optional
   DESCRIPTION
   "The serial number of the module."
   ::= { secondPickModule 11 }

modAssemAssem OBJECT-TYPE
   SYNTAX DisplayString
   ACCESS read-write
   STATUS optional
   DESCRIPTION
   "The assembly number of the module."
   ::= { secondPickModule 12 }

modAssemCode OBJECT-TYPE
   SYNTAX DisplayString
   ACCESS read-write
   STATUS optional
   DESCRIPTION
   "The manufacturing code of the module."
   ::= { secondPickModule 13 }

modPMDate OBJECT-TYPE
   SYNTAX DisplayString
   ACCESS read-write
   STATUS optional
   DESCRIPTION
   "Date of the last scheduled service of the module."
   ::= { secondPickModule 14 }

modPMData OBJECT-TYPE
   SYNTAX OCTET STRING
   ACCESS read-write
   STATUS optional
   DESCRIPTION
   "Details of the last scheduled service of the module."
   ::= { secondPickModule 15 }

-----------------------------------------------------------
-- Device Module Variable Table - secondPickModule
-----------------------------------------------------------

modVarTable OBJECT-TYPE
   SYNTAX  SEQUENCE OF ModVarEntry
   ACCESS  not-accessible
   STATUS  mandatory
   DESCRIPTION
   "This group defines the attributes of the variables used by the module to manage its operational state."
   ::= { secondPickModule 16 }

modVarEntry OBJECT-TYPE
    SYNTAX      ModVarEntry
    ACCESS      not-accessible
    STATUS      mandatory
    DESCRIPTION "This defines the contents of the table."
    INDEX      {modVarIndex}
    ::= {modVarTable 1}

ModVarEntry ::=
    SEQUENCE   {modVarIndex         INTEGER,
                modVarDesc          DisplayString,
                modVarType          VariableType,
                modVarValue         Counter,
                modVarThreshold1    INTEGER,
                modVarThreshold2    INTEGER}

modVarIndex OBJECT-TYPE
    SYNTAX      INTEGER
    ACCESS      read-only
    STATUS      mandatory
    DESCRIPTION "This is a unique number for every entry in the module 
                 variables table."
    ::= {modVarEntry 1}

modVarDesc OBJECT-TYPE
    SYNTAX      DisplayString
    ACCESS      read-only
    STATUS      mandatory
    DESCRIPTION "A description of the module variable."
    ::= {modVarEntry 2}

modVarType OBJECT-TYPE
    SYNTAX      VariableType
    ACCESS      read-only
    STATUS      mandatory
    DESCRIPTION "An enumerated value indicating whether the variable has
                 thresholds and the type of threshold."
    ::= {modVarEntry 3}

modVarValue OBJECT-TYPE
    SYNTAX      Counter
    ACCESS      read-only
    STATUS      mandatory
    DESCRIPTION "The value of the module variable."
    ::= {modVarEntry 4}

modVarThreshold1 OBJECT-TYPE
    SYNTAX      INTEGER
    ACCESS      read-write
    STATUS      optional
    DESCRIPTION "For variables with one threshold, this is a final value.
                 For variables with two thresholds, this is a warning value."
    ::= {modVarEntry 5}

modVarThreshold2 OBJECT-TYPE
    SYNTAX      INTEGER
    ACCESS      read-write
    STATUS      optional
    DESCRIPTION "For variables with two thresholds, this is the final value."
    ::= {modVarEntry 6}

-------------------------------------------------------------------------------
-- Device Module Actions Table - secondPickModule
-----------------------------------------------------------

modActionTable OBJECT-TYPE
   SYNTAX  SEQUENCE OF ModActionEntry
   ACCESS  not-accessible
   STATUS  mandatory
   DESCRIPTION
   "This group defines the attributes of the actions that can be performed on the module to restore or maintain its normal operational state."
   ::= { secondPickModule 17 }

modActionEntry OBJECT-TYPE
    SYNTAX      ModActionEntry
    ACCESS      not-accessible
    STATUS      mandatory
    DESCRIPTION "This defines the contents of the table."
    INDEX      {modActionIndex}
    ::= {modActionTable 1}

ModActionEntry ::=
    SEQUENCE   {modActionIndex               INTEGER,
                modActionDesc                DisplayString,
                modActionType                ActionType,
                modActionFaultDetect         TruthValue,
                modActionProactive           TruthValue,
                modActionProactiveDetect     TruthValue,
                modActionCustomerActionable  TruthValue,
                modActionComplete            TruthValue}

modActionIndex OBJECT-TYPE
    SYNTAX      INTEGER
    ACCESS      read-only
    STATUS      mandatory
    DESCRIPTION "A unique number for each action in the module actions table."
    ::= {modActionEntry 1}

modActionDesc OBJECT-TYPE
    SYNTAX      DisplayString
    ACCESS      read-only
    STATUS      mandatory
    DESCRIPTION "A description of the module action."
    ::= {modActionEntry 2}

modActionType OBJECT-TYPE
    SYNTAX      ActionType
    ACCESS      read-only
    STATUS      mandatory
    DESCRIPTION "An enumerated value indicating the type of action performed on
                 the module."
    ::= {modActionEntry 3}

modActionFaultDetect OBJECT-TYPE
    SYNTAX      TruthValue
    ACCESS      read-only
    STATUS      mandatory
    DESCRIPTION "A value of TRUE means the module can automatically detect that
                 the action has been performed for the associated fault that
                 was reported."
    ::= {modActionEntry 4}

modActionProactive OBJECT-TYPE
    SYNTAX      TruthValue
    ACCESS      read-only
    STATUS      mandatory
    DESCRIPTION "A value of TRUE means the action can be performed on the
                 module before the associated fault occurs."
    ::= {modActionEntry 5}

modActionProactiveDetect OBJECT-TYPE
    SYNTAX      TruthValue
    ACCESS      read-only
    STATUS      mandatory
    DESCRIPTION "A value of TRUE means the module can, through its sensors,
                 automatically detect that the action has been performed before
                 the associated fault occurs."
    ::= {modActionEntry 6}

modActionCustomerActionable OBJECT-TYPE
    SYNTAX      TruthValue
    ACCESS      read-only
    STATUS      mandatory
    DESCRIPTION "A value of TRUE means the customer can perform the action."
    ::= {modActionEntry 7}

modActionComplete OBJECT-TYPE
    SYNTAX      TruthValue
    ACCESS      write-only
    STATUS      mandatory
    DESCRIPTION "Setting the value of this attribute to TRUE informs the module
                 that the action has been performed, and clears the appropriate
                 module variables."
    ::= {modActionEntry 8}

END

CASH-01-USBDISPENSER-THIRDPICKMODULE-MIB DEFINITIONS ::= BEGIN

--
-- SST CASH-01-USBDISPENSER MIB
--

IMPORTS
    enterprises, Counter
        FROM RFC1155-SMI
    OBJECT-TYPE
        FROM RFC-1212
    DisplayString
        FROM RFC1213-MIB
    TruthValue
        FROM RFC1253-MIB
    sstDevice, VerificationState, ModuleState, VariableType, ActionType
        FROM NCR-CORESST-MIB;

    cash-01-UsbDispenser    OBJECT IDENTIFIER ::= { sstDevice 155 }
    thirdPickModule              OBJECT IDENTIFIER ::= { cash-01-UsbDispenser 8 }

-------------------------------------------------------------------------------
-- SST Device Module - thirdPickModule
-----------------------------------------------------------

modIdentifier OBJECT-TYPE
	SYNTAX INTEGER
   ACCESS read-only
   STATUS mandatory
   DESCRIPTION
   "Within the device, this is a unique identifier for the module."
   ::= { thirdPickModule 1 }

modDesc OBJECT-TYPE
   SYNTAX DisplayString
   ACCESS read-only
   STATUS mandatory
   DESCRIPTION
   "A description of the module."
   ::= { thirdPickModule 2 }

modReplenishable OBJECT-TYPE
   SYNTAX TruthValue
   ACCESS read-only
   STATUS mandatory
   DESCRIPTION
   "A value of TRUE means the module can be replenished (filled, emptied or renewed).
     A value of FALSE means it can be repaired or replaced."
   ::= { thirdPickModule 3 }

modCurrentSummaryState OBJECT-TYPE
   SYNTAX ModuleState
   ACCESS read-only
   STATUS mandatory
   DESCRIPTION
   "The current summary state of the module."
   ::= { thirdPickModule 4 }

modCurrentDetailedState OBJECT-TYPE
   SYNTAX INTEGER
   ACCESS read-only
   STATUS mandatory
   DESCRIPTION
   "The status code for the current detailed state."
   ::= { thirdPickModule 5 }

modCurrentDetailedStateDesc OBJECT-TYPE
   SYNTAX DisplayString
   ACCESS read-only
   STATUS mandatory
   DESCRIPTION
   "A description of the current detailed state."
   ::= { thirdPickModule 6 }

modPreviousSummaryState OBJECT-TYPE
   SYNTAX ModuleState
   ACCESS read-only
   STATUS mandatory
   DESCRIPTION
   "The previous summary state of the module."
   ::= { thirdPickModule 7 }

modPreviousDetailedState OBJECT-TYPE
   SYNTAX INTEGER
   ACCESS read-only
   STATUS mandatory
   DESCRIPTION
   "The status code for the previous detailed state."
   ::= { thirdPickModule 8 }

modPreviousDetailedStateDesc OBJECT-TYPE
   SYNTAX DisplayString
   ACCESS read-only
   STATUS mandatory
   DESCRIPTION
   "A description of the previous detailed state."
   ::= { thirdPickModule 9 }

modFaultId OBJECT-TYPE
   SYNTAX DisplayString
   ACCESS read-only
   STATUS mandatory
   DESCRIPTION
   "A string of digits summarizing all the information about the current state of the module."
   ::= { thirdPickModule 10 }

modAssemSerial OBJECT-TYPE
   SYNTAX DisplayString
   ACCESS read-write
   STATUS optional
   DESCRIPTION
   "The serial number of the module."
   ::= { thirdPickModule 11 }

modAssemAssem OBJECT-TYPE
   SYNTAX DisplayString
   ACCESS read-write
   STATUS optional
   DESCRIPTION
   "The assembly number of the module."
   ::= { thirdPickModule 12 }

modAssemCode OBJECT-TYPE
   SYNTAX DisplayString
   ACCESS read-write
   STATUS optional
   DESCRIPTION
   "The manufacturing code of the module."
   ::= { thirdPickModule 13 }

modPMDate OBJECT-TYPE
   SYNTAX DisplayString
   ACCESS read-write
   STATUS optional
   DESCRIPTION
   "Date of the last scheduled service of the module."
   ::= { thirdPickModule 14 }

modPMData OBJECT-TYPE
   SYNTAX OCTET STRING
   ACCESS read-write
   STATUS optional
   DESCRIPTION
   "Details of the last scheduled service of the module."
   ::= { thirdPickModule 15 }

-----------------------------------------------------------
-- Device Module Variable Table - thirdPickModule
-----------------------------------------------------------

modVarTable OBJECT-TYPE
   SYNTAX  SEQUENCE OF ModVarEntry
   ACCESS  not-accessible
   STATUS  mandatory
   DESCRIPTION
   "This group defines the attributes of the variables used by the module to manage its operational state."
   ::= { thirdPickModule 16 }

modVarEntry OBJECT-TYPE
    SYNTAX      ModVarEntry
    ACCESS      not-accessible
    STATUS      mandatory
    DESCRIPTION "This defines the contents of the table."
    INDEX      {modVarIndex}
    ::= {modVarTable 1}

ModVarEntry ::=
    SEQUENCE   {modVarIndex         INTEGER,
                modVarDesc          DisplayString,
                modVarType          VariableType,
                modVarValue         Counter,
                modVarThreshold1    INTEGER,
                modVarThreshold2    INTEGER}

modVarIndex OBJECT-TYPE
    SYNTAX      INTEGER
    ACCESS      read-only
    STATUS      mandatory
    DESCRIPTION "This is a unique number for every entry in the module 
                 variables table."
    ::= {modVarEntry 1}

modVarDesc OBJECT-TYPE
    SYNTAX      DisplayString
    ACCESS      read-only
    STATUS      mandatory
    DESCRIPTION "A description of the module variable."
    ::= {modVarEntry 2}

modVarType OBJECT-TYPE
    SYNTAX      VariableType
    ACCESS      read-only
    STATUS      mandatory
    DESCRIPTION "An enumerated value indicating whether the variable has
                 thresholds and the type of threshold."
    ::= {modVarEntry 3}

modVarValue OBJECT-TYPE
    SYNTAX      Counter
    ACCESS      read-only
    STATUS      mandatory
    DESCRIPTION "The value of the module variable."
    ::= {modVarEntry 4}

modVarThreshold1 OBJECT-TYPE
    SYNTAX      INTEGER
    ACCESS      read-write
    STATUS      optional
    DESCRIPTION "For variables with one threshold, this is a final value.
                 For variables with two thresholds, this is a warning value."
    ::= {modVarEntry 5}

modVarThreshold2 OBJECT-TYPE
    SYNTAX      INTEGER
    ACCESS      read-write
    STATUS      optional
    DESCRIPTION "For variables with two thresholds, this is the final value."
    ::= {modVarEntry 6}

-------------------------------------------------------------------------------
-- Device Module Actions Table - thirdPickModule
-----------------------------------------------------------

modActionTable OBJECT-TYPE
   SYNTAX  SEQUENCE OF ModActionEntry
   ACCESS  not-accessible
   STATUS  mandatory
   DESCRIPTION
   "This group defines the attributes of the actions that can be performed on the module to restore or maintain its normal operational state."
   ::= { thirdPickModule 17 }

modActionEntry OBJECT-TYPE
    SYNTAX      ModActionEntry
    ACCESS      not-accessible
    STATUS      mandatory
    DESCRIPTION "This defines the contents of the table."
    INDEX      {modActionIndex}
    ::= {modActionTable 1}

ModActionEntry ::=
    SEQUENCE   {modActionIndex               INTEGER,
                modActionDesc                DisplayString,
                modActionType                ActionType,
                modActionFaultDetect         TruthValue,
                modActionProactive           TruthValue,
                modActionProactiveDetect     TruthValue,
                modActionCustomerActionable  TruthValue,
                modActionComplete            TruthValue}

modActionIndex OBJECT-TYPE
    SYNTAX      INTEGER
    ACCESS      read-only
    STATUS      mandatory
    DESCRIPTION "A unique number for each action in the module actions table."
    ::= {modActionEntry 1}

modActionDesc OBJECT-TYPE
    SYNTAX      DisplayString
    ACCESS      read-only
    STATUS      mandatory
    DESCRIPTION "A description of the module action."
    ::= {modActionEntry 2}

modActionType OBJECT-TYPE
    SYNTAX      ActionType
    ACCESS      read-only
    STATUS      mandatory
    DESCRIPTION "An enumerated value indicating the type of action performed on
                 the module."
    ::= {modActionEntry 3}

modActionFaultDetect OBJECT-TYPE
    SYNTAX      TruthValue
    ACCESS      read-only
    STATUS      mandatory
    DESCRIPTION "A value of TRUE means the module can automatically detect that
                 the action has been performed for the associated fault that
                 was reported."
    ::= {modActionEntry 4}

modActionProactive OBJECT-TYPE
    SYNTAX      TruthValue
    ACCESS      read-only
    STATUS      mandatory
    DESCRIPTION "A value of TRUE means the action can be performed on the
                 module before the associated fault occurs."
    ::= {modActionEntry 5}

modActionProactiveDetect OBJECT-TYPE
    SYNTAX      TruthValue
    ACCESS      read-only
    STATUS      mandatory
    DESCRIPTION "A value of TRUE means the module can, through its sensors,
                 automatically detect that the action has been performed before
                 the associated fault occurs."
    ::= {modActionEntry 6}

modActionCustomerActionable OBJECT-TYPE
    SYNTAX      TruthValue
    ACCESS      read-only
    STATUS      mandatory
    DESCRIPTION "A value of TRUE means the customer can perform the action."
    ::= {modActionEntry 7}

modActionComplete OBJECT-TYPE
    SYNTAX      TruthValue
    ACCESS      write-only
    STATUS      mandatory
    DESCRIPTION "Setting the value of this attribute to TRUE informs the module
                 that the action has been performed, and clears the appropriate
                 module variables."
    ::= {modActionEntry 8}

END

CASH-01-USBDISPENSER-BOTTOMPICKMODULE-MIB DEFINITIONS ::= BEGIN

--
-- SST CASH-01-USBDISPENSER MIB
--

IMPORTS
    enterprises, Counter
        FROM RFC1155-SMI
    OBJECT-TYPE
        FROM RFC-1212
    DisplayString
        FROM RFC1213-MIB
    TruthValue
        FROM RFC1253-MIB
    sstDevice, VerificationState, ModuleState, VariableType, ActionType
        FROM NCR-CORESST-MIB;

    cash-01-UsbDispenser    OBJECT IDENTIFIER ::= { sstDevice 155 }
    bottomPickModule              OBJECT IDENTIFIER ::= { cash-01-UsbDispenser 9 }

-------------------------------------------------------------------------------
-- SST Device Module - bottomPickModule
-----------------------------------------------------------

modIdentifier OBJECT-TYPE
	SYNTAX INTEGER
   ACCESS read-only
   STATUS mandatory
   DESCRIPTION
   "Within the device, this is a unique identifier for the module."
   ::= { bottomPickModule 1 }

modDesc OBJECT-TYPE
   SYNTAX DisplayString
   ACCESS read-only
   STATUS mandatory
   DESCRIPTION
   "A description of the module."
   ::= { bottomPickModule 2 }

modReplenishable OBJECT-TYPE
   SYNTAX TruthValue
   ACCESS read-only
   STATUS mandatory
   DESCRIPTION
   "A value of TRUE means the module can be replenished (filled, emptied or renewed).
     A value of FALSE means it can be repaired or replaced."
   ::= { bottomPickModule 3 }

modCurrentSummaryState OBJECT-TYPE
   SYNTAX ModuleState
   ACCESS read-only
   STATUS mandatory
   DESCRIPTION
   "The current summary state of the module."
   ::= { bottomPickModule 4 }

modCurrentDetailedState OBJECT-TYPE
   SYNTAX INTEGER
   ACCESS read-only
   STATUS mandatory
   DESCRIPTION
   "The status code for the current detailed state."
   ::= { bottomPickModule 5 }

modCurrentDetailedStateDesc OBJECT-TYPE
   SYNTAX DisplayString
   ACCESS read-only
   STATUS mandatory
   DESCRIPTION
   "A description of the current detailed state."
   ::= { bottomPickModule 6 }

modPreviousSummaryState OBJECT-TYPE
   SYNTAX ModuleState
   ACCESS read-only
   STATUS mandatory
   DESCRIPTION
   "The previous summary state of the module."
   ::= { bottomPickModule 7 }

modPreviousDetailedState OBJECT-TYPE
   SYNTAX INTEGER
   ACCESS read-only
   STATUS mandatory
   DESCRIPTION
   "The status code for the previous detailed state."
   ::= { bottomPickModule 8 }

modPreviousDetailedStateDesc OBJECT-TYPE
   SYNTAX DisplayString
   ACCESS read-only
   STATUS mandatory
   DESCRIPTION
   "A description of the previous detailed state."
   ::= { bottomPickModule 9 }

modFaultId OBJECT-TYPE
   SYNTAX DisplayString
   ACCESS read-only
   STATUS mandatory
   DESCRIPTION
   "A string of digits summarizing all the information about the current state of the module."
   ::= { bottomPickModule 10 }

modAssemSerial OBJECT-TYPE
   SYNTAX DisplayString
   ACCESS read-write
   STATUS optional
   DESCRIPTION
   "The serial number of the module."
   ::= { bottomPickModule 11 }

modAssemAssem OBJECT-TYPE
   SYNTAX DisplayString
   ACCESS read-write
   STATUS optional
   DESCRIPTION
   "The assembly number of the module."
   ::= { bottomPickModule 12 }

modAssemCode OBJECT-TYPE
   SYNTAX DisplayString
   ACCESS read-write
   STATUS optional
   DESCRIPTION
   "The manufacturing code of the module."
   ::= { bottomPickModule 13 }

modPMDate OBJECT-TYPE
   SYNTAX DisplayString
   ACCESS read-write
   STATUS optional
   DESCRIPTION
   "Date of the last scheduled service of the module."
   ::= { bottomPickModule 14 }

modPMData OBJECT-TYPE
   SYNTAX OCTET STRING
   ACCESS read-write
   STATUS optional
   DESCRIPTION
   "Details of the last scheduled service of the module."
   ::= { bottomPickModule 15 }

-----------------------------------------------------------
-- Device Module Variable Table - bottomPickModule
-----------------------------------------------------------

modVarTable OBJECT-TYPE
   SYNTAX  SEQUENCE OF ModVarEntry
   ACCESS  not-accessible
   STATUS  mandatory
   DESCRIPTION
   "This group defines the attributes of the variables used by the module to manage its operational state."
   ::= { bottomPickModule 16 }

modVarEntry OBJECT-TYPE
    SYNTAX      ModVarEntry
    ACCESS      not-accessible
    STATUS      mandatory
    DESCRIPTION "This defines the contents of the table."
    INDEX      {modVarIndex}
    ::= {modVarTable 1}

ModVarEntry ::=
    SEQUENCE   {modVarIndex         INTEGER,
                modVarDesc          DisplayString,
                modVarType          VariableType,
                modVarValue         Counter,
                modVarThreshold1    INTEGER,
                modVarThreshold2    INTEGER}

modVarIndex OBJECT-TYPE
    SYNTAX      INTEGER
    ACCESS      read-only
    STATUS      mandatory
    DESCRIPTION "This is a unique number for every entry in the module 
                 variables table."
    ::= {modVarEntry 1}

modVarDesc OBJECT-TYPE
    SYNTAX      DisplayString
    ACCESS      read-only
    STATUS      mandatory
    DESCRIPTION "A description of the module variable."
    ::= {modVarEntry 2}

modVarType OBJECT-TYPE
    SYNTAX      VariableType
    ACCESS      read-only
    STATUS      mandatory
    DESCRIPTION "An enumerated value indicating whether the variable has
                 thresholds and the type of threshold."
    ::= {modVarEntry 3}

modVarValue OBJECT-TYPE
    SYNTAX      Counter
    ACCESS      read-only
    STATUS      mandatory
    DESCRIPTION "The value of the module variable."
    ::= {modVarEntry 4}

modVarThreshold1 OBJECT-TYPE
    SYNTAX      INTEGER
    ACCESS      read-write
    STATUS      optional
    DESCRIPTION "For variables with one threshold, this is a final value.
                 For variables with two thresholds, this is a warning value."
    ::= {modVarEntry 5}

modVarThreshold2 OBJECT-TYPE
    SYNTAX      INTEGER
    ACCESS      read-write
    STATUS      optional
    DESCRIPTION "For variables with two thresholds, this is the final value."
    ::= {modVarEntry 6}

-------------------------------------------------------------------------------
-- Device Module Actions Table - bottomPickModule
-----------------------------------------------------------

modActionTable OBJECT-TYPE
   SYNTAX  SEQUENCE OF ModActionEntry
   ACCESS  not-accessible
   STATUS  mandatory
   DESCRIPTION
   "This group defines the attributes of the actions that can be performed on the module to restore or maintain its normal operational state."
   ::= { bottomPickModule 17 }

modActionEntry OBJECT-TYPE
    SYNTAX      ModActionEntry
    ACCESS      not-accessible
    STATUS      mandatory
    DESCRIPTION "This defines the contents of the table."
    INDEX      {modActionIndex}
    ::= {modActionTable 1}

ModActionEntry ::=
    SEQUENCE   {modActionIndex               INTEGER,
                modActionDesc                DisplayString,
                modActionType                ActionType,
                modActionFaultDetect         TruthValue,
                modActionProactive           TruthValue,
                modActionProactiveDetect     TruthValue,
                modActionCustomerActionable  TruthValue,
                modActionComplete            TruthValue}

modActionIndex OBJECT-TYPE
    SYNTAX      INTEGER
    ACCESS      read-only
    STATUS      mandatory
    DESCRIPTION "A unique number for each action in the module actions table."
    ::= {modActionEntry 1}

modActionDesc OBJECT-TYPE
    SYNTAX      DisplayString
    ACCESS      read-only
    STATUS      mandatory
    DESCRIPTION "A description of the module action."
    ::= {modActionEntry 2}

modActionType OBJECT-TYPE
    SYNTAX      ActionType
    ACCESS      read-only
    STATUS      mandatory
    DESCRIPTION "An enumerated value indicating the type of action performed on
                 the module."
    ::= {modActionEntry 3}

modActionFaultDetect OBJECT-TYPE
    SYNTAX      TruthValue
    ACCESS      read-only
    STATUS      mandatory
    DESCRIPTION "A value of TRUE means the module can automatically detect that
                 the action has been performed for the associated fault that
                 was reported."
    ::= {modActionEntry 4}

modActionProactive OBJECT-TYPE
    SYNTAX      TruthValue
    ACCESS      read-only
    STATUS      mandatory
    DESCRIPTION "A value of TRUE means the action can be performed on the
                 module before the associated fault occurs."
    ::= {modActionEntry 5}

modActionProactiveDetect OBJECT-TYPE
    SYNTAX      TruthValue
    ACCESS      read-only
    STATUS      mandatory
    DESCRIPTION "A value of TRUE means the module can, through its sensors,
                 automatically detect that the action has been performed before
                 the associated fault occurs."
    ::= {modActionEntry 6}

modActionCustomerActionable OBJECT-TYPE
    SYNTAX      TruthValue
    ACCESS      read-only
    STATUS      mandatory
    DESCRIPTION "A value of TRUE means the customer can perform the action."
    ::= {modActionEntry 7}

modActionComplete OBJECT-TYPE
    SYNTAX      TruthValue
    ACCESS      write-only
    STATUS      mandatory
    DESCRIPTION "Setting the value of this attribute to TRUE informs the module
                 that the action has been performed, and clears the appropriate
                 module variables."
    ::= {modActionEntry 8}

END

CASH-01-USBDISPENSER-TOPCASSETTE-MIB DEFINITIONS ::= BEGIN

--
-- SST CASH-01-USBDISPENSER MIB
--

IMPORTS
    enterprises, Counter
        FROM RFC1155-SMI
    OBJECT-TYPE
        FROM RFC-1212
    DisplayString
        FROM RFC1213-MIB
    TruthValue
        FROM RFC1253-MIB
    sstDevice, VerificationState, ModuleState, VariableType, ActionType
        FROM NCR-CORESST-MIB;

    cash-01-UsbDispenser    OBJECT IDENTIFIER ::= { sstDevice 155 }
    topCassette              OBJECT IDENTIFIER ::= { cash-01-UsbDispenser 10 }

-------------------------------------------------------------------------------
-- SST Device Module - topCassette
-----------------------------------------------------------

modIdentifier OBJECT-TYPE
	SYNTAX INTEGER
   ACCESS read-only
   STATUS mandatory
   DESCRIPTION
   "Within the device, this is a unique identifier for the module."
   ::= { topCassette 1 }

modDesc OBJECT-TYPE
   SYNTAX DisplayString
   ACCESS read-only
   STATUS mandatory
   DESCRIPTION
   "A description of the module."
   ::= { topCassette 2 }

modReplenishable OBJECT-TYPE
   SYNTAX TruthValue
   ACCESS read-only
   STATUS mandatory
   DESCRIPTION
   "A value of TRUE means the module can be replenished (filled, emptied or renewed).
     A value of FALSE means it can be repaired or replaced."
   ::= { topCassette 3 }

modCurrentSummaryState OBJECT-TYPE
   SYNTAX ModuleState
   ACCESS read-only
   STATUS mandatory
   DESCRIPTION
   "The current summary state of the module."
   ::= { topCassette 4 }

modCurrentDetailedState OBJECT-TYPE
   SYNTAX INTEGER
   ACCESS read-only
   STATUS mandatory
   DESCRIPTION
   "The status code for the current detailed state."
   ::= { topCassette 5 }

modCurrentDetailedStateDesc OBJECT-TYPE
   SYNTAX DisplayString
   ACCESS read-only
   STATUS mandatory
   DESCRIPTION
   "A description of the current detailed state."
   ::= { topCassette 6 }

modPreviousSummaryState OBJECT-TYPE
   SYNTAX ModuleState
   ACCESS read-only
   STATUS mandatory
   DESCRIPTION
   "The previous summary state of the module."
   ::= { topCassette 7 }

modPreviousDetailedState OBJECT-TYPE
   SYNTAX INTEGER
   ACCESS read-only
   STATUS mandatory
   DESCRIPTION
   "The status code for the previous detailed state."
   ::= { topCassette 8 }

modPreviousDetailedStateDesc OBJECT-TYPE
   SYNTAX DisplayString
   ACCESS read-only
   STATUS mandatory
   DESCRIPTION
   "A description of the previous detailed state."
   ::= { topCassette 9 }

modFaultId OBJECT-TYPE
   SYNTAX DisplayString
   ACCESS read-only
   STATUS mandatory
   DESCRIPTION
   "A string of digits summarizing all the information about the current state of the module."
   ::= { topCassette 10 }

modAssemSerial OBJECT-TYPE
   SYNTAX DisplayString
   ACCESS read-write
   STATUS optional
   DESCRIPTION
   "The serial number of the module."
   ::= { topCassette 11 }

modAssemAssem OBJECT-TYPE
   SYNTAX DisplayString
   ACCESS read-write
   STATUS optional
   DESCRIPTION
   "The assembly number of the module."
   ::= { topCassette 12 }

modAssemCode OBJECT-TYPE
   SYNTAX DisplayString
   ACCESS read-write
   STATUS optional
   DESCRIPTION
   "The manufacturing code of the module."
   ::= { topCassette 13 }

modPMDate OBJECT-TYPE
   SYNTAX DisplayString
   ACCESS read-write
   STATUS optional
   DESCRIPTION
   "Date of the last scheduled service of the module."
   ::= { topCassette 14 }

modPMData OBJECT-TYPE
   SYNTAX OCTET STRING
   ACCESS read-write
   STATUS optional
   DESCRIPTION
   "Details of the last scheduled service of the module."
   ::= { topCassette 15 }

-----------------------------------------------------------
-- Device Module Variable Table - topCassette
-----------------------------------------------------------

modVarTable OBJECT-TYPE
   SYNTAX  SEQUENCE OF ModVarEntry
   ACCESS  not-accessible
   STATUS  mandatory
   DESCRIPTION
   "This group defines the attributes of the variables used by the module to manage its operational state."
   ::= { topCassette 16 }

modVarEntry OBJECT-TYPE
    SYNTAX      ModVarEntry
    ACCESS      not-accessible
    STATUS      mandatory
    DESCRIPTION "This defines the contents of the table."
    INDEX      {modVarIndex}
    ::= {modVarTable 1}

ModVarEntry ::=
    SEQUENCE   {modVarIndex         INTEGER,
                modVarDesc          DisplayString,
                modVarType          VariableType,
                modVarValue         Counter,
                modVarThreshold1    INTEGER,
                modVarThreshold2    INTEGER}

modVarIndex OBJECT-TYPE
    SYNTAX      INTEGER
    ACCESS      read-only
    STATUS      mandatory
    DESCRIPTION "This is a unique number for every entry in the module 
                 variables table."
    ::= {modVarEntry 1}

modVarDesc OBJECT-TYPE
    SYNTAX      DisplayString
    ACCESS      read-only
    STATUS      mandatory
    DESCRIPTION "A description of the module variable."
    ::= {modVarEntry 2}

modVarType OBJECT-TYPE
    SYNTAX      VariableType
    ACCESS      read-only
    STATUS      mandatory
    DESCRIPTION "An enumerated value indicating whether the variable has
                 thresholds and the type of threshold."
    ::= {modVarEntry 3}

modVarValue OBJECT-TYPE
    SYNTAX      Counter
    ACCESS      read-only
    STATUS      mandatory
    DESCRIPTION "The value of the module variable."
    ::= {modVarEntry 4}

modVarThreshold1 OBJECT-TYPE
    SYNTAX      INTEGER
    ACCESS      read-write
    STATUS      optional
    DESCRIPTION "For variables with one threshold, this is a final value.
                 For variables with two thresholds, this is a warning value."
    ::= {modVarEntry 5}

modVarThreshold2 OBJECT-TYPE
    SYNTAX      INTEGER
    ACCESS      read-write
    STATUS      optional
    DESCRIPTION "For variables with two thresholds, this is the final value."
    ::= {modVarEntry 6}

-------------------------------------------------------------------------------
-- Device Module Actions Table - topCassette
-----------------------------------------------------------

modActionTable OBJECT-TYPE
   SYNTAX  SEQUENCE OF ModActionEntry
   ACCESS  not-accessible
   STATUS  mandatory
   DESCRIPTION
   "This group defines the attributes of the actions that can be performed on the module to restore or maintain its normal operational state."
   ::= { topCassette 17 }

modActionEntry OBJECT-TYPE
    SYNTAX      ModActionEntry
    ACCESS      not-accessible
    STATUS      mandatory
    DESCRIPTION "This defines the contents of the table."
    INDEX      {modActionIndex}
    ::= {modActionTable 1}

ModActionEntry ::=
    SEQUENCE   {modActionIndex               INTEGER,
                modActionDesc                DisplayString,
                modActionType                ActionType,
                modActionFaultDetect         TruthValue,
                modActionProactive           TruthValue,
                modActionProactiveDetect     TruthValue,
                modActionCustomerActionable  TruthValue,
                modActionComplete            TruthValue}

modActionIndex OBJECT-TYPE
    SYNTAX      INTEGER
    ACCESS      read-only
    STATUS      mandatory
    DESCRIPTION "A unique number for each action in the module actions table."
    ::= {modActionEntry 1}

modActionDesc OBJECT-TYPE
    SYNTAX      DisplayString
    ACCESS      read-only
    STATUS      mandatory
    DESCRIPTION "A description of the module action."
    ::= {modActionEntry 2}

modActionType OBJECT-TYPE
    SYNTAX      ActionType
    ACCESS      read-only
    STATUS      mandatory
    DESCRIPTION "An enumerated value indicating the type of action performed on
                 the module."
    ::= {modActionEntry 3}

modActionFaultDetect OBJECT-TYPE
    SYNTAX      TruthValue
    ACCESS      read-only
    STATUS      mandatory
    DESCRIPTION "A value of TRUE means the module can automatically detect that
                 the action has been performed for the associated fault that
                 was reported."
    ::= {modActionEntry 4}

modActionProactive OBJECT-TYPE
    SYNTAX      TruthValue
    ACCESS      read-only
    STATUS      mandatory
    DESCRIPTION "A value of TRUE means the action can be performed on the
                 module before the associated fault occurs."
    ::= {modActionEntry 5}

modActionProactiveDetect OBJECT-TYPE
    SYNTAX      TruthValue
    ACCESS      read-only
    STATUS      mandatory
    DESCRIPTION "A value of TRUE means the module can, through its sensors,
                 automatically detect that the action has been performed before
                 the associated fault occurs."
    ::= {modActionEntry 6}

modActionCustomerActionable OBJECT-TYPE
    SYNTAX      TruthValue
    ACCESS      read-only
    STATUS      mandatory
    DESCRIPTION "A value of TRUE means the customer can perform the action."
    ::= {modActionEntry 7}

modActionComplete OBJECT-TYPE
    SYNTAX      TruthValue
    ACCESS      write-only
    STATUS      mandatory
    DESCRIPTION "Setting the value of this attribute to TRUE informs the module
                 that the action has been performed, and clears the appropriate
                 module variables."
    ::= {modActionEntry 8}

END

CASH-01-USBDISPENSER-SECONDCASSETTE-MIB DEFINITIONS ::= BEGIN

--
-- SST CASH-01-USBDISPENSER MIB
--

IMPORTS
    enterprises, Counter
        FROM RFC1155-SMI
    OBJECT-TYPE
        FROM RFC-1212
    DisplayString
        FROM RFC1213-MIB
    TruthValue
        FROM RFC1253-MIB
    sstDevice, VerificationState, ModuleState, VariableType, ActionType
        FROM NCR-CORESST-MIB;

    cash-01-UsbDispenser    OBJECT IDENTIFIER ::= { sstDevice 155 }
    secondCassette              OBJECT IDENTIFIER ::= { cash-01-UsbDispenser 11 }

-------------------------------------------------------------------------------
-- SST Device Module - secondCassette
-----------------------------------------------------------

modIdentifier OBJECT-TYPE
	SYNTAX INTEGER
   ACCESS read-only
   STATUS mandatory
   DESCRIPTION
   "Within the device, this is a unique identifier for the module."
   ::= { secondCassette 1 }

modDesc OBJECT-TYPE
   SYNTAX DisplayString
   ACCESS read-only
   STATUS mandatory
   DESCRIPTION
   "A description of the module."
   ::= { secondCassette 2 }

modReplenishable OBJECT-TYPE
   SYNTAX TruthValue
   ACCESS read-only
   STATUS mandatory
   DESCRIPTION
   "A value of TRUE means the module can be replenished (filled, emptied or renewed).
     A value of FALSE means it can be repaired or replaced."
   ::= { secondCassette 3 }

modCurrentSummaryState OBJECT-TYPE
   SYNTAX ModuleState
   ACCESS read-only
   STATUS mandatory
   DESCRIPTION
   "The current summary state of the module."
   ::= { secondCassette 4 }

modCurrentDetailedState OBJECT-TYPE
   SYNTAX INTEGER
   ACCESS read-only
   STATUS mandatory
   DESCRIPTION
   "The status code for the current detailed state."
   ::= { secondCassette 5 }

modCurrentDetailedStateDesc OBJECT-TYPE
   SYNTAX DisplayString
   ACCESS read-only
   STATUS mandatory
   DESCRIPTION
   "A description of the current detailed state."
   ::= { secondCassette 6 }

modPreviousSummaryState OBJECT-TYPE
   SYNTAX ModuleState
   ACCESS read-only
   STATUS mandatory
   DESCRIPTION
   "The previous summary state of the module."
   ::= { secondCassette 7 }

modPreviousDetailedState OBJECT-TYPE
   SYNTAX INTEGER
   ACCESS read-only
   STATUS mandatory
   DESCRIPTION
   "The status code for the previous detailed state."
   ::= { secondCassette 8 }

modPreviousDetailedStateDesc OBJECT-TYPE
   SYNTAX DisplayString
   ACCESS read-only
   STATUS mandatory
   DESCRIPTION
   "A description of the previous detailed state."
   ::= { secondCassette 9 }

modFaultId OBJECT-TYPE
   SYNTAX DisplayString
   ACCESS read-only
   STATUS mandatory
   DESCRIPTION
   "A string of digits summarizing all the information about the current state of the module."
   ::= { secondCassette 10 }

modAssemSerial OBJECT-TYPE
   SYNTAX DisplayString
   ACCESS read-write
   STATUS optional
   DESCRIPTION
   "The serial number of the module."
   ::= { secondCassette 11 }

modAssemAssem OBJECT-TYPE
   SYNTAX DisplayString
   ACCESS read-write
   STATUS optional
   DESCRIPTION
   "The assembly number of the module."
   ::= { secondCassette 12 }

modAssemCode OBJECT-TYPE
   SYNTAX DisplayString
   ACCESS read-write
   STATUS optional
   DESCRIPTION
   "The manufacturing code of the module."
   ::= { secondCassette 13 }

modPMDate OBJECT-TYPE
   SYNTAX DisplayString
   ACCESS read-write
   STATUS optional
   DESCRIPTION
   "Date of the last scheduled service of the module."
   ::= { secondCassette 14 }

modPMData OBJECT-TYPE
   SYNTAX OCTET STRING
   ACCESS read-write
   STATUS optional
   DESCRIPTION
   "Details of the last scheduled service of the module."
   ::= { secondCassette 15 }

-----------------------------------------------------------
-- Device Module Variable Table - secondCassette
-----------------------------------------------------------

modVarTable OBJECT-TYPE
   SYNTAX  SEQUENCE OF ModVarEntry
   ACCESS  not-accessible
   STATUS  mandatory
   DESCRIPTION
   "This group defines the attributes of the variables used by the module to manage its operational state."
   ::= { secondCassette 16 }

modVarEntry OBJECT-TYPE
    SYNTAX      ModVarEntry
    ACCESS      not-accessible
    STATUS      mandatory
    DESCRIPTION "This defines the contents of the table."
    INDEX      {modVarIndex}
    ::= {modVarTable 1}

ModVarEntry ::=
    SEQUENCE   {modVarIndex         INTEGER,
                modVarDesc          DisplayString,
                modVarType          VariableType,
                modVarValue         Counter,
                modVarThreshold1    INTEGER,
                modVarThreshold2    INTEGER}

modVarIndex OBJECT-TYPE
    SYNTAX      INTEGER
    ACCESS      read-only
    STATUS      mandatory
    DESCRIPTION "This is a unique number for every entry in the module 
                 variables table."
    ::= {modVarEntry 1}

modVarDesc OBJECT-TYPE
    SYNTAX      DisplayString
    ACCESS      read-only
    STATUS      mandatory
    DESCRIPTION "A description of the module variable."
    ::= {modVarEntry 2}

modVarType OBJECT-TYPE
    SYNTAX      VariableType
    ACCESS      read-only
    STATUS      mandatory
    DESCRIPTION "An enumerated value indicating whether the variable has
                 thresholds and the type of threshold."
    ::= {modVarEntry 3}

modVarValue OBJECT-TYPE
    SYNTAX      Counter
    ACCESS      read-only
    STATUS      mandatory
    DESCRIPTION "The value of the module variable."
    ::= {modVarEntry 4}

modVarThreshold1 OBJECT-TYPE
    SYNTAX      INTEGER
    ACCESS      read-write
    STATUS      optional
    DESCRIPTION "For variables with one threshold, this is a final value.
                 For variables with two thresholds, this is a warning value."
    ::= {modVarEntry 5}

modVarThreshold2 OBJECT-TYPE
    SYNTAX      INTEGER
    ACCESS      read-write
    STATUS      optional
    DESCRIPTION "For variables with two thresholds, this is the final value."
    ::= {modVarEntry 6}

-------------------------------------------------------------------------------
-- Device Module Actions Table - secondCassette
-----------------------------------------------------------

modActionTable OBJECT-TYPE
   SYNTAX  SEQUENCE OF ModActionEntry
   ACCESS  not-accessible
   STATUS  mandatory
   DESCRIPTION
   "This group defines the attributes of the actions that can be performed on the module to restore or maintain its normal operational state."
   ::= { secondCassette 17 }

modActionEntry OBJECT-TYPE
    SYNTAX      ModActionEntry
    ACCESS      not-accessible
    STATUS      mandatory
    DESCRIPTION "This defines the contents of the table."
    INDEX      {modActionIndex}
    ::= {modActionTable 1}

ModActionEntry ::=
    SEQUENCE   {modActionIndex               INTEGER,
                modActionDesc                DisplayString,
                modActionType                ActionType,
                modActionFaultDetect         TruthValue,
                modActionProactive           TruthValue,
                modActionProactiveDetect     TruthValue,
                modActionCustomerActionable  TruthValue,
                modActionComplete            TruthValue}

modActionIndex OBJECT-TYPE
    SYNTAX      INTEGER
    ACCESS      read-only
    STATUS      mandatory
    DESCRIPTION "A unique number for each action in the module actions table."
    ::= {modActionEntry 1}

modActionDesc OBJECT-TYPE
    SYNTAX      DisplayString
    ACCESS      read-only
    STATUS      mandatory
    DESCRIPTION "A description of the module action."
    ::= {modActionEntry 2}

modActionType OBJECT-TYPE
    SYNTAX      ActionType
    ACCESS      read-only
    STATUS      mandatory
    DESCRIPTION "An enumerated value indicating the type of action performed on
                 the module."
    ::= {modActionEntry 3}

modActionFaultDetect OBJECT-TYPE
    SYNTAX      TruthValue
    ACCESS      read-only
    STATUS      mandatory
    DESCRIPTION "A value of TRUE means the module can automatically detect that
                 the action has been performed for the associated fault that
                 was reported."
    ::= {modActionEntry 4}

modActionProactive OBJECT-TYPE
    SYNTAX      TruthValue
    ACCESS      read-only
    STATUS      mandatory
    DESCRIPTION "A value of TRUE means the action can be performed on the
                 module before the associated fault occurs."
    ::= {modActionEntry 5}

modActionProactiveDetect OBJECT-TYPE
    SYNTAX      TruthValue
    ACCESS      read-only
    STATUS      mandatory
    DESCRIPTION "A value of TRUE means the module can, through its sensors,
                 automatically detect that the action has been performed before
                 the associated fault occurs."
    ::= {modActionEntry 6}

modActionCustomerActionable OBJECT-TYPE
    SYNTAX      TruthValue
    ACCESS      read-only
    STATUS      mandatory
    DESCRIPTION "A value of TRUE means the customer can perform the action."
    ::= {modActionEntry 7}

modActionComplete OBJECT-TYPE
    SYNTAX      TruthValue
    ACCESS      write-only
    STATUS      mandatory
    DESCRIPTION "Setting the value of this attribute to TRUE informs the module
                 that the action has been performed, and clears the appropriate
                 module variables."
    ::= {modActionEntry 8}

END

CASH-01-USBDISPENSER-THIRDCASSETTE-MIB DEFINITIONS ::= BEGIN

--
-- SST CASH-01-USBDISPENSER MIB
--

IMPORTS
    enterprises, Counter
        FROM RFC1155-SMI
    OBJECT-TYPE
        FROM RFC-1212
    DisplayString
        FROM RFC1213-MIB
    TruthValue
        FROM RFC1253-MIB
    sstDevice, VerificationState, ModuleState, VariableType, ActionType
        FROM NCR-CORESST-MIB;

    cash-01-UsbDispenser    OBJECT IDENTIFIER ::= { sstDevice 155 }
    thirdCassette              OBJECT IDENTIFIER ::= { cash-01-UsbDispenser 12 }

-------------------------------------------------------------------------------
-- SST Device Module - thirdCassette
-----------------------------------------------------------

modIdentifier OBJECT-TYPE
	SYNTAX INTEGER
   ACCESS read-only
   STATUS mandatory
   DESCRIPTION
   "Within the device, this is a unique identifier for the module."
   ::= { thirdCassette 1 }

modDesc OBJECT-TYPE
   SYNTAX DisplayString
   ACCESS read-only
   STATUS mandatory
   DESCRIPTION
   "A description of the module."
   ::= { thirdCassette 2 }

modReplenishable OBJECT-TYPE
   SYNTAX TruthValue
   ACCESS read-only
   STATUS mandatory
   DESCRIPTION
   "A value of TRUE means the module can be replenished (filled, emptied or renewed).
     A value of FALSE means it can be repaired or replaced."
   ::= { thirdCassette 3 }

modCurrentSummaryState OBJECT-TYPE
   SYNTAX ModuleState
   ACCESS read-only
   STATUS mandatory
   DESCRIPTION
   "The current summary state of the module."
   ::= { thirdCassette 4 }

modCurrentDetailedState OBJECT-TYPE
   SYNTAX INTEGER
   ACCESS read-only
   STATUS mandatory
   DESCRIPTION
   "The status code for the current detailed state."
   ::= { thirdCassette 5 }

modCurrentDetailedStateDesc OBJECT-TYPE
   SYNTAX DisplayString
   ACCESS read-only
   STATUS mandatory
   DESCRIPTION
   "A description of the current detailed state."
   ::= { thirdCassette 6 }

modPreviousSummaryState OBJECT-TYPE
   SYNTAX ModuleState
   ACCESS read-only
   STATUS mandatory
   DESCRIPTION
   "The previous summary state of the module."
   ::= { thirdCassette 7 }

modPreviousDetailedState OBJECT-TYPE
   SYNTAX INTEGER
   ACCESS read-only
   STATUS mandatory
   DESCRIPTION
   "The status code for the previous detailed state."
   ::= { thirdCassette 8 }

modPreviousDetailedStateDesc OBJECT-TYPE
   SYNTAX DisplayString
   ACCESS read-only
   STATUS mandatory
   DESCRIPTION
   "A description of the previous detailed state."
   ::= { thirdCassette 9 }

modFaultId OBJECT-TYPE
   SYNTAX DisplayString
   ACCESS read-only
   STATUS mandatory
   DESCRIPTION
   "A string of digits summarizing all the information about the current state of the module."
   ::= { thirdCassette 10 }

modAssemSerial OBJECT-TYPE
   SYNTAX DisplayString
   ACCESS read-write
   STATUS optional
   DESCRIPTION
   "The serial number of the module."
   ::= { thirdCassette 11 }

modAssemAssem OBJECT-TYPE
   SYNTAX DisplayString
   ACCESS read-write
   STATUS optional
   DESCRIPTION
   "The assembly number of the module."
   ::= { thirdCassette 12 }

modAssemCode OBJECT-TYPE
   SYNTAX DisplayString
   ACCESS read-write
   STATUS optional
   DESCRIPTION
   "The manufacturing code of the module."
   ::= { thirdCassette 13 }

modPMDate OBJECT-TYPE
   SYNTAX DisplayString
   ACCESS read-write
   STATUS optional
   DESCRIPTION
   "Date of the last scheduled service of the module."
   ::= { thirdCassette 14 }

modPMData OBJECT-TYPE
   SYNTAX OCTET STRING
   ACCESS read-write
   STATUS optional
   DESCRIPTION
   "Details of the last scheduled service of the module."
   ::= { thirdCassette 15 }

-----------------------------------------------------------
-- Device Module Variable Table - thirdCassette
-----------------------------------------------------------

modVarTable OBJECT-TYPE
   SYNTAX  SEQUENCE OF ModVarEntry
   ACCESS  not-accessible
   STATUS  mandatory
   DESCRIPTION
   "This group defines the attributes of the variables used by the module to manage its operational state."
   ::= { thirdCassette 16 }

modVarEntry OBJECT-TYPE
    SYNTAX      ModVarEntry
    ACCESS      not-accessible
    STATUS      mandatory
    DESCRIPTION "This defines the contents of the table."
    INDEX      {modVarIndex}
    ::= {modVarTable 1}

ModVarEntry ::=
    SEQUENCE   {modVarIndex         INTEGER,
                modVarDesc          DisplayString,
                modVarType          VariableType,
                modVarValue         Counter,
                modVarThreshold1    INTEGER,
                modVarThreshold2    INTEGER}

modVarIndex OBJECT-TYPE
    SYNTAX      INTEGER
    ACCESS      read-only
    STATUS      mandatory
    DESCRIPTION "This is a unique number for every entry in the module 
                 variables table."
    ::= {modVarEntry 1}

modVarDesc OBJECT-TYPE
    SYNTAX      DisplayString
    ACCESS      read-only
    STATUS      mandatory
    DESCRIPTION "A description of the module variable."
    ::= {modVarEntry 2}

modVarType OBJECT-TYPE
    SYNTAX      VariableType
    ACCESS      read-only
    STATUS      mandatory
    DESCRIPTION "An enumerated value indicating whether the variable has
                 thresholds and the type of threshold."
    ::= {modVarEntry 3}

modVarValue OBJECT-TYPE
    SYNTAX      Counter
    ACCESS      read-only
    STATUS      mandatory
    DESCRIPTION "The value of the module variable."
    ::= {modVarEntry 4}

modVarThreshold1 OBJECT-TYPE
    SYNTAX      INTEGER
    ACCESS      read-write
    STATUS      optional
    DESCRIPTION "For variables with one threshold, this is a final value.
                 For variables with two thresholds, this is a warning value."
    ::= {modVarEntry 5}

modVarThreshold2 OBJECT-TYPE
    SYNTAX      INTEGER
    ACCESS      read-write
    STATUS      optional
    DESCRIPTION "For variables with two thresholds, this is the final value."
    ::= {modVarEntry 6}

-------------------------------------------------------------------------------
-- Device Module Actions Table - thirdCassette
-----------------------------------------------------------

modActionTable OBJECT-TYPE
   SYNTAX  SEQUENCE OF ModActionEntry
   ACCESS  not-accessible
   STATUS  mandatory
   DESCRIPTION
   "This group defines the attributes of the actions that can be performed on the module to restore or maintain its normal operational state."
   ::= { thirdCassette 17 }

modActionEntry OBJECT-TYPE
    SYNTAX      ModActionEntry
    ACCESS      not-accessible
    STATUS      mandatory
    DESCRIPTION "This defines the contents of the table."
    INDEX      {modActionIndex}
    ::= {modActionTable 1}

ModActionEntry ::=
    SEQUENCE   {modActionIndex               INTEGER,
                modActionDesc                DisplayString,
                modActionType                ActionType,
                modActionFaultDetect         TruthValue,
                modActionProactive           TruthValue,
                modActionProactiveDetect     TruthValue,
                modActionCustomerActionable  TruthValue,
                modActionComplete            TruthValue}

modActionIndex OBJECT-TYPE
    SYNTAX      INTEGER
    ACCESS      read-only
    STATUS      mandatory
    DESCRIPTION "A unique number for each action in the module actions table."
    ::= {modActionEntry 1}

modActionDesc OBJECT-TYPE
    SYNTAX      DisplayString
    ACCESS      read-only
    STATUS      mandatory
    DESCRIPTION "A description of the module action."
    ::= {modActionEntry 2}

modActionType OBJECT-TYPE
    SYNTAX      ActionType
    ACCESS      read-only
    STATUS      mandatory
    DESCRIPTION "An enumerated value indicating the type of action performed on
                 the module."
    ::= {modActionEntry 3}

modActionFaultDetect OBJECT-TYPE
    SYNTAX      TruthValue
    ACCESS      read-only
    STATUS      mandatory
    DESCRIPTION "A value of TRUE means the module can automatically detect that
                 the action has been performed for the associated fault that
                 was reported."
    ::= {modActionEntry 4}

modActionProactive OBJECT-TYPE
    SYNTAX      TruthValue
    ACCESS      read-only
    STATUS      mandatory
    DESCRIPTION "A value of TRUE means the action can be performed on the
                 module before the associated fault occurs."
    ::= {modActionEntry 5}

modActionProactiveDetect OBJECT-TYPE
    SYNTAX      TruthValue
    ACCESS      read-only
    STATUS      mandatory
    DESCRIPTION "A value of TRUE means the module can, through its sensors,
                 automatically detect that the action has been performed before
                 the associated fault occurs."
    ::= {modActionEntry 6}

modActionCustomerActionable OBJECT-TYPE
    SYNTAX      TruthValue
    ACCESS      read-only
    STATUS      mandatory
    DESCRIPTION "A value of TRUE means the customer can perform the action."
    ::= {modActionEntry 7}

modActionComplete OBJECT-TYPE
    SYNTAX      TruthValue
    ACCESS      write-only
    STATUS      mandatory
    DESCRIPTION "Setting the value of this attribute to TRUE informs the module
                 that the action has been performed, and clears the appropriate
                 module variables."
    ::= {modActionEntry 8}

END

CASH-01-USBDISPENSER-BOTTOMCASSETTE-MIB DEFINITIONS ::= BEGIN

--
-- SST CASH-01-USBDISPENSER MIB
--

IMPORTS
    enterprises, Counter
        FROM RFC1155-SMI
    OBJECT-TYPE
        FROM RFC-1212
    DisplayString
        FROM RFC1213-MIB
    TruthValue
        FROM RFC1253-MIB
    sstDevice, VerificationState, ModuleState, VariableType, ActionType
        FROM NCR-CORESST-MIB;

    cash-01-UsbDispenser    OBJECT IDENTIFIER ::= { sstDevice 155 }
    bottomCassette              OBJECT IDENTIFIER ::= { cash-01-UsbDispenser 13 }

-------------------------------------------------------------------------------
-- SST Device Module - bottomCassette
-----------------------------------------------------------

modIdentifier OBJECT-TYPE
	SYNTAX INTEGER
   ACCESS read-only
   STATUS mandatory
   DESCRIPTION
   "Within the device, this is a unique identifier for the module."
   ::= { bottomCassette 1 }

modDesc OBJECT-TYPE
   SYNTAX DisplayString
   ACCESS read-only
   STATUS mandatory
   DESCRIPTION
   "A description of the module."
   ::= { bottomCassette 2 }

modReplenishable OBJECT-TYPE
   SYNTAX TruthValue
   ACCESS read-only
   STATUS mandatory
   DESCRIPTION
   "A value of TRUE means the module can be replenished (filled, emptied or renewed).
     A value of FALSE means it can be repaired or replaced."
   ::= { bottomCassette 3 }

modCurrentSummaryState OBJECT-TYPE
   SYNTAX ModuleState
   ACCESS read-only
   STATUS mandatory
   DESCRIPTION
   "The current summary state of the module."
   ::= { bottomCassette 4 }

modCurrentDetailedState OBJECT-TYPE
   SYNTAX INTEGER
   ACCESS read-only
   STATUS mandatory
   DESCRIPTION
   "The status code for the current detailed state."
   ::= { bottomCassette 5 }

modCurrentDetailedStateDesc OBJECT-TYPE
   SYNTAX DisplayString
   ACCESS read-only
   STATUS mandatory
   DESCRIPTION
   "A description of the current detailed state."
   ::= { bottomCassette 6 }

modPreviousSummaryState OBJECT-TYPE
   SYNTAX ModuleState
   ACCESS read-only
   STATUS mandatory
   DESCRIPTION
   "The previous summary state of the module."
   ::= { bottomCassette 7 }

modPreviousDetailedState OBJECT-TYPE
   SYNTAX INTEGER
   ACCESS read-only
   STATUS mandatory
   DESCRIPTION
   "The status code for the previous detailed state."
   ::= { bottomCassette 8 }

modPreviousDetailedStateDesc OBJECT-TYPE
   SYNTAX DisplayString
   ACCESS read-only
   STATUS mandatory
   DESCRIPTION
   "A description of the previous detailed state."
   ::= { bottomCassette 9 }

modFaultId OBJECT-TYPE
   SYNTAX DisplayString
   ACCESS read-only
   STATUS mandatory
   DESCRIPTION
   "A string of digits summarizing all the information about the current state of the module."
   ::= { bottomCassette 10 }

modAssemSerial OBJECT-TYPE
   SYNTAX DisplayString
   ACCESS read-write
   STATUS optional
   DESCRIPTION
   "The serial number of the module."
   ::= { bottomCassette 11 }

modAssemAssem OBJECT-TYPE
   SYNTAX DisplayString
   ACCESS read-write
   STATUS optional
   DESCRIPTION
   "The assembly number of the module."
   ::= { bottomCassette 12 }

modAssemCode OBJECT-TYPE
   SYNTAX DisplayString
   ACCESS read-write
   STATUS optional
   DESCRIPTION
   "The manufacturing code of the module."
   ::= { bottomCassette 13 }

modPMDate OBJECT-TYPE
   SYNTAX DisplayString
   ACCESS read-write
   STATUS optional
   DESCRIPTION
   "Date of the last scheduled service of the module."
   ::= { bottomCassette 14 }

modPMData OBJECT-TYPE
   SYNTAX OCTET STRING
   ACCESS read-write
   STATUS optional
   DESCRIPTION
   "Details of the last scheduled service of the module."
   ::= { bottomCassette 15 }

-----------------------------------------------------------
-- Device Module Variable Table - bottomCassette
-----------------------------------------------------------

modVarTable OBJECT-TYPE
   SYNTAX  SEQUENCE OF ModVarEntry
   ACCESS  not-accessible
   STATUS  mandatory
   DESCRIPTION
   "This group defines the attributes of the variables used by the module to manage its operational state."
   ::= { bottomCassette 16 }

modVarEntry OBJECT-TYPE
    SYNTAX      ModVarEntry
    ACCESS      not-accessible
    STATUS      mandatory
    DESCRIPTION "This defines the contents of the table."
    INDEX      {modVarIndex}
    ::= {modVarTable 1}

ModVarEntry ::=
    SEQUENCE   {modVarIndex         INTEGER,
                modVarDesc          DisplayString,
                modVarType          VariableType,
                modVarValue         Counter,
                modVarThreshold1    INTEGER,
                modVarThreshold2    INTEGER}

modVarIndex OBJECT-TYPE
    SYNTAX      INTEGER
    ACCESS      read-only
    STATUS      mandatory
    DESCRIPTION "This is a unique number for every entry in the module 
                 variables table."
    ::= {modVarEntry 1}

modVarDesc OBJECT-TYPE
    SYNTAX      DisplayString
    ACCESS      read-only
    STATUS      mandatory
    DESCRIPTION "A description of the module variable."
    ::= {modVarEntry 2}

modVarType OBJECT-TYPE
    SYNTAX      VariableType
    ACCESS      read-only
    STATUS      mandatory
    DESCRIPTION "An enumerated value indicating whether the variable has
                 thresholds and the type of threshold."
    ::= {modVarEntry 3}

modVarValue OBJECT-TYPE
    SYNTAX      Counter
    ACCESS      read-only
    STATUS      mandatory
    DESCRIPTION "The value of the module variable."
    ::= {modVarEntry 4}

modVarThreshold1 OBJECT-TYPE
    SYNTAX      INTEGER
    ACCESS      read-write
    STATUS      optional
    DESCRIPTION "For variables with one threshold, this is a final value.
                 For variables with two thresholds, this is a warning value."
    ::= {modVarEntry 5}

modVarThreshold2 OBJECT-TYPE
    SYNTAX      INTEGER
    ACCESS      read-write
    STATUS      optional
    DESCRIPTION "For variables with two thresholds, this is the final value."
    ::= {modVarEntry 6}

-------------------------------------------------------------------------------
-- Device Module Actions Table - bottomCassette
-----------------------------------------------------------

modActionTable OBJECT-TYPE
   SYNTAX  SEQUENCE OF ModActionEntry
   ACCESS  not-accessible
   STATUS  mandatory
   DESCRIPTION
   "This group defines the attributes of the actions that can be performed on the module to restore or maintain its normal operational state."
   ::= { bottomCassette 17 }

modActionEntry OBJECT-TYPE
    SYNTAX      ModActionEntry
    ACCESS      not-accessible
    STATUS      mandatory
    DESCRIPTION "This defines the contents of the table."
    INDEX      {modActionIndex}
    ::= {modActionTable 1}

ModActionEntry ::=
    SEQUENCE   {modActionIndex               INTEGER,
                modActionDesc                DisplayString,
                modActionType                ActionType,
                modActionFaultDetect         TruthValue,
                modActionProactive           TruthValue,
                modActionProactiveDetect     TruthValue,
                modActionCustomerActionable  TruthValue,
                modActionComplete            TruthValue}

modActionIndex OBJECT-TYPE
    SYNTAX      INTEGER
    ACCESS      read-only
    STATUS      mandatory
    DESCRIPTION "A unique number for each action in the module actions table."
    ::= {modActionEntry 1}

modActionDesc OBJECT-TYPE
    SYNTAX      DisplayString
    ACCESS      read-only
    STATUS      mandatory
    DESCRIPTION "A description of the module action."
    ::= {modActionEntry 2}

modActionType OBJECT-TYPE
    SYNTAX      ActionType
    ACCESS      read-only
    STATUS      mandatory
    DESCRIPTION "An enumerated value indicating the type of action performed on
                 the module."
    ::= {modActionEntry 3}

modActionFaultDetect OBJECT-TYPE
    SYNTAX      TruthValue
    ACCESS      read-only
    STATUS      mandatory
    DESCRIPTION "A value of TRUE means the module can automatically detect that
                 the action has been performed for the associated fault that
                 was reported."
    ::= {modActionEntry 4}

modActionProactive OBJECT-TYPE
    SYNTAX      TruthValue
    ACCESS      read-only
    STATUS      mandatory
    DESCRIPTION "A value of TRUE means the action can be performed on the
                 module before the associated fault occurs."
    ::= {modActionEntry 5}

modActionProactiveDetect OBJECT-TYPE
    SYNTAX      TruthValue
    ACCESS      read-only
    STATUS      mandatory
    DESCRIPTION "A value of TRUE means the module can, through its sensors,
                 automatically detect that the action has been performed before
                 the associated fault occurs."
    ::= {modActionEntry 6}

modActionCustomerActionable OBJECT-TYPE
    SYNTAX      TruthValue
    ACCESS      read-only
    STATUS      mandatory
    DESCRIPTION "A value of TRUE means the customer can perform the action."
    ::= {modActionEntry 7}

modActionComplete OBJECT-TYPE
    SYNTAX      TruthValue
    ACCESS      write-only
    STATUS      mandatory
    DESCRIPTION "Setting the value of this attribute to TRUE informs the module
                 that the action has been performed, and clears the appropriate
                 module variables."
    ::= {modActionEntry 8}

END

CASH-01-USBDISPENSER-PURGEBIN-MIB DEFINITIONS ::= BEGIN

--
-- SST CASH-01-USBDISPENSER MIB
--

IMPORTS
    enterprises, Counter
        FROM RFC1155-SMI
    OBJECT-TYPE
        FROM RFC-1212
    DisplayString
        FROM RFC1213-MIB
    TruthValue
        FROM RFC1253-MIB
    sstDevice, VerificationState, ModuleState, VariableType, ActionType
        FROM NCR-CORESST-MIB;

    cash-01-UsbDispenser    OBJECT IDENTIFIER ::= { sstDevice 155 }
    purgeBin              OBJECT IDENTIFIER ::= { cash-01-UsbDispenser 14 }

-------------------------------------------------------------------------------
-- SST Device Module - purgeBin
-----------------------------------------------------------

modIdentifier OBJECT-TYPE
	SYNTAX INTEGER
   ACCESS read-only
   STATUS mandatory
   DESCRIPTION
   "Within the device, this is a unique identifier for the module."
   ::= { purgeBin 1 }

modDesc OBJECT-TYPE
   SYNTAX DisplayString
   ACCESS read-only
   STATUS mandatory
   DESCRIPTION
   "A description of the module."
   ::= { purgeBin 2 }

modReplenishable OBJECT-TYPE
   SYNTAX TruthValue
   ACCESS read-only
   STATUS mandatory
   DESCRIPTION
   "A value of TRUE means the module can be replenished (filled, emptied or renewed).
     A value of FALSE means it can be repaired or replaced."
   ::= { purgeBin 3 }

modCurrentSummaryState OBJECT-TYPE
   SYNTAX ModuleState
   ACCESS read-only
   STATUS mandatory
   DESCRIPTION
   "The current summary state of the module."
   ::= { purgeBin 4 }

modCurrentDetailedState OBJECT-TYPE
   SYNTAX INTEGER
   ACCESS read-only
   STATUS mandatory
   DESCRIPTION
   "The status code for the current detailed state."
   ::= { purgeBin 5 }

modCurrentDetailedStateDesc OBJECT-TYPE
   SYNTAX DisplayString
   ACCESS read-only
   STATUS mandatory
   DESCRIPTION
   "A description of the current detailed state."
   ::= { purgeBin 6 }

modPreviousSummaryState OBJECT-TYPE
   SYNTAX ModuleState
   ACCESS read-only
   STATUS mandatory
   DESCRIPTION
   "The previous summary state of the module."
   ::= { purgeBin 7 }

modPreviousDetailedState OBJECT-TYPE
   SYNTAX INTEGER
   ACCESS read-only
   STATUS mandatory
   DESCRIPTION
   "The status code for the previous detailed state."
   ::= { purgeBin 8 }

modPreviousDetailedStateDesc OBJECT-TYPE
   SYNTAX DisplayString
   ACCESS read-only
   STATUS mandatory
   DESCRIPTION
   "A description of the previous detailed state."
   ::= { purgeBin 9 }

modFaultId OBJECT-TYPE
   SYNTAX DisplayString
   ACCESS read-only
   STATUS mandatory
   DESCRIPTION
   "A string of digits summarizing all the information about the current state of the module."
   ::= { purgeBin 10 }

modAssemSerial OBJECT-TYPE
   SYNTAX DisplayString
   ACCESS read-write
   STATUS optional
   DESCRIPTION
   "The serial number of the module."
   ::= { purgeBin 11 }

modAssemAssem OBJECT-TYPE
   SYNTAX DisplayString
   ACCESS read-write
   STATUS optional
   DESCRIPTION
   "The assembly number of the module."
   ::= { purgeBin 12 }

modAssemCode OBJECT-TYPE
   SYNTAX DisplayString
   ACCESS read-write
   STATUS optional
   DESCRIPTION
   "The manufacturing code of the module."
   ::= { purgeBin 13 }

modPMDate OBJECT-TYPE
   SYNTAX DisplayString
   ACCESS read-write
   STATUS optional
   DESCRIPTION
   "Date of the last scheduled service of the module."
   ::= { purgeBin 14 }

modPMData OBJECT-TYPE
   SYNTAX OCTET STRING
   ACCESS read-write
   STATUS optional
   DESCRIPTION
   "Details of the last scheduled service of the module."
   ::= { purgeBin 15 }

-----------------------------------------------------------
-- Device Module Variable Table - purgeBin
-----------------------------------------------------------

modVarTable OBJECT-TYPE
   SYNTAX  SEQUENCE OF ModVarEntry
   ACCESS  not-accessible
   STATUS  mandatory
   DESCRIPTION
   "This group defines the attributes of the variables used by the module to manage its operational state."
   ::= { purgeBin 16 }

modVarEntry OBJECT-TYPE
    SYNTAX      ModVarEntry
    ACCESS      not-accessible
    STATUS      mandatory
    DESCRIPTION "This defines the contents of the table."
    INDEX      {modVarIndex}
    ::= {modVarTable 1}

ModVarEntry ::=
    SEQUENCE   {modVarIndex         INTEGER,
                modVarDesc          DisplayString,
                modVarType          VariableType,
                modVarValue         Counter,
                modVarThreshold1    INTEGER,
                modVarThreshold2    INTEGER}

modVarIndex OBJECT-TYPE
    SYNTAX      INTEGER
    ACCESS      read-only
    STATUS      mandatory
    DESCRIPTION "This is a unique number for every entry in the module 
                 variables table."
    ::= {modVarEntry 1}

modVarDesc OBJECT-TYPE
    SYNTAX      DisplayString
    ACCESS      read-only
    STATUS      mandatory
    DESCRIPTION "A description of the module variable."
    ::= {modVarEntry 2}

modVarType OBJECT-TYPE
    SYNTAX      VariableType
    ACCESS      read-only
    STATUS      mandatory
    DESCRIPTION "An enumerated value indicating whether the variable has
                 thresholds and the type of threshold."
    ::= {modVarEntry 3}

modVarValue OBJECT-TYPE
    SYNTAX      Counter
    ACCESS      read-only
    STATUS      mandatory
    DESCRIPTION "The value of the module variable."
    ::= {modVarEntry 4}

modVarThreshold1 OBJECT-TYPE
    SYNTAX      INTEGER
    ACCESS      read-write
    STATUS      optional
    DESCRIPTION "For variables with one threshold, this is a final value.
                 For variables with two thresholds, this is a warning value."
    ::= {modVarEntry 5}

modVarThreshold2 OBJECT-TYPE
    SYNTAX      INTEGER
    ACCESS      read-write
    STATUS      optional
    DESCRIPTION "For variables with two thresholds, this is the final value."
    ::= {modVarEntry 6}

-------------------------------------------------------------------------------
-- Device Module Actions Table - purgeBin
-----------------------------------------------------------

modActionTable OBJECT-TYPE
   SYNTAX  SEQUENCE OF ModActionEntry
   ACCESS  not-accessible
   STATUS  mandatory
   DESCRIPTION
   "This group defines the attributes of the actions that can be performed on the module to restore or maintain its normal operational state."
   ::= { purgeBin 17 }

modActionEntry OBJECT-TYPE
    SYNTAX      ModActionEntry
    ACCESS      not-accessible
    STATUS      mandatory
    DESCRIPTION "This defines the contents of the table."
    INDEX      {modActionIndex}
    ::= {modActionTable 1}

ModActionEntry ::=
    SEQUENCE   {modActionIndex               INTEGER,
                modActionDesc                DisplayString,
                modActionType                ActionType,
                modActionFaultDetect         TruthValue,
                modActionProactive           TruthValue,
                modActionProactiveDetect     TruthValue,
                modActionCustomerActionable  TruthValue,
                modActionComplete            TruthValue}

modActionIndex OBJECT-TYPE
    SYNTAX      INTEGER
    ACCESS      read-only
    STATUS      mandatory
    DESCRIPTION "A unique number for each action in the module actions table."
    ::= {modActionEntry 1}

modActionDesc OBJECT-TYPE
    SYNTAX      DisplayString
    ACCESS      read-only
    STATUS      mandatory
    DESCRIPTION "A description of the module action."
    ::= {modActionEntry 2}

modActionType OBJECT-TYPE
    SYNTAX      ActionType
    ACCESS      read-only
    STATUS      mandatory
    DESCRIPTION "An enumerated value indicating the type of action performed on
                 the module."
    ::= {modActionEntry 3}

modActionFaultDetect OBJECT-TYPE
    SYNTAX      TruthValue
    ACCESS      read-only
    STATUS      mandatory
    DESCRIPTION "A value of TRUE means the module can automatically detect that
                 the action has been performed for the associated fault that
                 was reported."
    ::= {modActionEntry 4}

modActionProactive OBJECT-TYPE
    SYNTAX      TruthValue
    ACCESS      read-only
    STATUS      mandatory
    DESCRIPTION "A value of TRUE means the action can be performed on the
                 module before the associated fault occurs."
    ::= {modActionEntry 5}

modActionProactiveDetect OBJECT-TYPE
    SYNTAX      TruthValue
    ACCESS      read-only
    STATUS      mandatory
    DESCRIPTION "A value of TRUE means the module can, through its sensors,
                 automatically detect that the action has been performed before
                 the associated fault occurs."
    ::= {modActionEntry 6}

modActionCustomerActionable OBJECT-TYPE
    SYNTAX      TruthValue
    ACCESS      read-only
    STATUS      mandatory
    DESCRIPTION "A value of TRUE means the customer can perform the action."
    ::= {modActionEntry 7}

modActionComplete OBJECT-TYPE
    SYNTAX      TruthValue
    ACCESS      write-only
    STATUS      mandatory
    DESCRIPTION "Setting the value of this attribute to TRUE informs the module
                 that the action has been performed, and clears the appropriate
                 module variables."
    ::= {modActionEntry 8}

END

CASH-01-USBDISPENSER-PRESENTER-MIB DEFINITIONS ::= BEGIN

--
-- SST CASH-01-USBDISPENSER MIB
--

IMPORTS
    enterprises, Counter
        FROM RFC1155-SMI
    OBJECT-TYPE
        FROM RFC-1212
    DisplayString
        FROM RFC1213-MIB
    TruthValue
        FROM RFC1253-MIB
    sstDevice, VerificationState, ModuleState, VariableType, ActionType
        FROM NCR-CORESST-MIB;

    cash-01-UsbDispenser    OBJECT IDENTIFIER ::= { sstDevice 155 }
    presenter              OBJECT IDENTIFIER ::= { cash-01-UsbDispenser 15 }

-------------------------------------------------------------------------------
-- SST Device Module - presenter
-----------------------------------------------------------

modIdentifier OBJECT-TYPE
	SYNTAX INTEGER
   ACCESS read-only
   STATUS mandatory
   DESCRIPTION
   "Within the device, this is a unique identifier for the module."
   ::= { presenter 1 }

modDesc OBJECT-TYPE
   SYNTAX DisplayString
   ACCESS read-only
   STATUS mandatory
   DESCRIPTION
   "A description of the module."
   ::= { presenter 2 }

modReplenishable OBJECT-TYPE
   SYNTAX TruthValue
   ACCESS read-only
   STATUS mandatory
   DESCRIPTION
   "A value of TRUE means the module can be replenished (filled, emptied or renewed).
     A value of FALSE means it can be repaired or replaced."
   ::= { presenter 3 }

modCurrentSummaryState OBJECT-TYPE
   SYNTAX ModuleState
   ACCESS read-only
   STATUS mandatory
   DESCRIPTION
   "The current summary state of the module."
   ::= { presenter 4 }

modCurrentDetailedState OBJECT-TYPE
   SYNTAX INTEGER
   ACCESS read-only
   STATUS mandatory
   DESCRIPTION
   "The status code for the current detailed state."
   ::= { presenter 5 }

modCurrentDetailedStateDesc OBJECT-TYPE
   SYNTAX DisplayString
   ACCESS read-only
   STATUS mandatory
   DESCRIPTION
   "A description of the current detailed state."
   ::= { presenter 6 }

modPreviousSummaryState OBJECT-TYPE
   SYNTAX ModuleState
   ACCESS read-only
   STATUS mandatory
   DESCRIPTION
   "The previous summary state of the module."
   ::= { presenter 7 }

modPreviousDetailedState OBJECT-TYPE
   SYNTAX INTEGER
   ACCESS read-only
   STATUS mandatory
   DESCRIPTION
   "The status code for the previous detailed state."
   ::= { presenter 8 }

modPreviousDetailedStateDesc OBJECT-TYPE
   SYNTAX DisplayString
   ACCESS read-only
   STATUS mandatory
   DESCRIPTION
   "A description of the previous detailed state."
   ::= { presenter 9 }

modFaultId OBJECT-TYPE
   SYNTAX DisplayString
   ACCESS read-only
   STATUS mandatory
   DESCRIPTION
   "A string of digits summarizing all the information about the current state of the module."
   ::= { presenter 10 }

modAssemSerial OBJECT-TYPE
   SYNTAX DisplayString
   ACCESS read-write
   STATUS optional
   DESCRIPTION
   "The serial number of the module."
   ::= { presenter 11 }

modAssemAssem OBJECT-TYPE
   SYNTAX DisplayString
   ACCESS read-write
   STATUS optional
   DESCRIPTION
   "The assembly number of the module."
   ::= { presenter 12 }

modAssemCode OBJECT-TYPE
   SYNTAX DisplayString
   ACCESS read-write
   STATUS optional
   DESCRIPTION
   "The manufacturing code of the module."
   ::= { presenter 13 }

modPMDate OBJECT-TYPE
   SYNTAX DisplayString
   ACCESS read-write
   STATUS optional
   DESCRIPTION
   "Date of the last scheduled service of the module."
   ::= { presenter 14 }

modPMData OBJECT-TYPE
   SYNTAX OCTET STRING
   ACCESS read-write
   STATUS optional
   DESCRIPTION
   "Details of the last scheduled service of the module."
   ::= { presenter 15 }

-----------------------------------------------------------
-- Device Module Variable Table - presenter
-----------------------------------------------------------

modVarTable OBJECT-TYPE
   SYNTAX  SEQUENCE OF ModVarEntry
   ACCESS  not-accessible
   STATUS  mandatory
   DESCRIPTION
   "This group defines the attributes of the variables used by the module to manage its operational state."
   ::= { presenter 16 }

modVarEntry OBJECT-TYPE
    SYNTAX      ModVarEntry
    ACCESS      not-accessible
    STATUS      mandatory
    DESCRIPTION "This defines the contents of the table."
    INDEX      {modVarIndex}
    ::= {modVarTable 1}

ModVarEntry ::=
    SEQUENCE   {modVarIndex         INTEGER,
                modVarDesc          DisplayString,
                modVarType          VariableType,
                modVarValue         Counter,
                modVarThreshold1    INTEGER,
                modVarThreshold2    INTEGER}

modVarIndex OBJECT-TYPE
    SYNTAX      INTEGER
    ACCESS      read-only
    STATUS      mandatory
    DESCRIPTION "This is a unique number for every entry in the module 
                 variables table."
    ::= {modVarEntry 1}

modVarDesc OBJECT-TYPE
    SYNTAX      DisplayString
    ACCESS      read-only
    STATUS      mandatory
    DESCRIPTION "A description of the module variable."
    ::= {modVarEntry 2}

modVarType OBJECT-TYPE
    SYNTAX      VariableType
    ACCESS      read-only
    STATUS      mandatory
    DESCRIPTION "An enumerated value indicating whether the variable has
                 thresholds and the type of threshold."
    ::= {modVarEntry 3}

modVarValue OBJECT-TYPE
    SYNTAX      Counter
    ACCESS      read-only
    STATUS      mandatory
    DESCRIPTION "The value of the module variable."
    ::= {modVarEntry 4}

modVarThreshold1 OBJECT-TYPE
    SYNTAX      INTEGER
    ACCESS      read-write
    STATUS      optional
    DESCRIPTION "For variables with one threshold, this is a final value.
                 For variables with two thresholds, this is a warning value."
    ::= {modVarEntry 5}

modVarThreshold2 OBJECT-TYPE
    SYNTAX      INTEGER
    ACCESS      read-write
    STATUS      optional
    DESCRIPTION "For variables with two thresholds, this is the final value."
    ::= {modVarEntry 6}

-------------------------------------------------------------------------------
-- Device Module Actions Table - presenter
-----------------------------------------------------------

modActionTable OBJECT-TYPE
   SYNTAX  SEQUENCE OF ModActionEntry
   ACCESS  not-accessible
   STATUS  mandatory
   DESCRIPTION
   "This group defines the attributes of the actions that can be performed on the module to restore or maintain its normal operational state."
   ::= { presenter 17 }

modActionEntry OBJECT-TYPE
    SYNTAX      ModActionEntry
    ACCESS      not-accessible
    STATUS      mandatory
    DESCRIPTION "This defines the contents of the table."
    INDEX      {modActionIndex}
    ::= {modActionTable 1}

ModActionEntry ::=
    SEQUENCE   {modActionIndex               INTEGER,
                modActionDesc                DisplayString,
                modActionType                ActionType,
                modActionFaultDetect         TruthValue,
                modActionProactive           TruthValue,
                modActionProactiveDetect     TruthValue,
                modActionCustomerActionable  TruthValue,
                modActionComplete            TruthValue}

modActionIndex OBJECT-TYPE
    SYNTAX      INTEGER
    ACCESS      read-only
    STATUS      mandatory
    DESCRIPTION "A unique number for each action in the module actions table."
    ::= {modActionEntry 1}

modActionDesc OBJECT-TYPE
    SYNTAX      DisplayString
    ACCESS      read-only
    STATUS      mandatory
    DESCRIPTION "A description of the module action."
    ::= {modActionEntry 2}

modActionType OBJECT-TYPE
    SYNTAX      ActionType
    ACCESS      read-only
    STATUS      mandatory
    DESCRIPTION "An enumerated value indicating the type of action performed on
                 the module."
    ::= {modActionEntry 3}

modActionFaultDetect OBJECT-TYPE
    SYNTAX      TruthValue
    ACCESS      read-only
    STATUS      mandatory
    DESCRIPTION "A value of TRUE means the module can automatically detect that
                 the action has been performed for the associated fault that
                 was reported."
    ::= {modActionEntry 4}

modActionProactive OBJECT-TYPE
    SYNTAX      TruthValue
    ACCESS      read-only
    STATUS      mandatory
    DESCRIPTION "A value of TRUE means the action can be performed on the
                 module before the associated fault occurs."
    ::= {modActionEntry 5}

modActionProactiveDetect OBJECT-TYPE
    SYNTAX      TruthValue
    ACCESS      read-only
    STATUS      mandatory
    DESCRIPTION "A value of TRUE means the module can, through its sensors,
                 automatically detect that the action has been performed before
                 the associated fault occurs."
    ::= {modActionEntry 6}

modActionCustomerActionable OBJECT-TYPE
    SYNTAX      TruthValue
    ACCESS      read-only
    STATUS      mandatory
    DESCRIPTION "A value of TRUE means the customer can perform the action."
    ::= {modActionEntry 7}

modActionComplete OBJECT-TYPE
    SYNTAX      TruthValue
    ACCESS      write-only
    STATUS      mandatory
    DESCRIPTION "Setting the value of this attribute to TRUE informs the module
                 that the action has been performed, and clears the appropriate
                 module variables."
    ::= {modActionEntry 8}

END

CASH-01-USBDISPENSER-EXITSHUTTER-MIB DEFINITIONS ::= BEGIN

--
-- SST CASH-01-USBDISPENSER MIB
--

IMPORTS
    enterprises, Counter
        FROM RFC1155-SMI
    OBJECT-TYPE
        FROM RFC-1212
    DisplayString
        FROM RFC1213-MIB
    TruthValue
        FROM RFC1253-MIB
    sstDevice, VerificationState, ModuleState, VariableType, ActionType
        FROM NCR-CORESST-MIB;

    cash-01-UsbDispenser    OBJECT IDENTIFIER ::= { sstDevice 155 }
    exitShutter              OBJECT IDENTIFIER ::= { cash-01-UsbDispenser 16 }

-------------------------------------------------------------------------------
-- SST Device Module - exitShutter
-----------------------------------------------------------

modIdentifier OBJECT-TYPE
	SYNTAX INTEGER
   ACCESS read-only
   STATUS mandatory
   DESCRIPTION
   "Within the device, this is a unique identifier for the module."
   ::= { exitShutter 1 }

modDesc OBJECT-TYPE
   SYNTAX DisplayString
   ACCESS read-only
   STATUS mandatory
   DESCRIPTION
   "A description of the module."
   ::= { exitShutter 2 }

modReplenishable OBJECT-TYPE
   SYNTAX TruthValue
   ACCESS read-only
   STATUS mandatory
   DESCRIPTION
   "A value of TRUE means the module can be replenished (filled, emptied or renewed).
     A value of FALSE means it can be repaired or replaced."
   ::= { exitShutter 3 }

modCurrentSummaryState OBJECT-TYPE
   SYNTAX ModuleState
   ACCESS read-only
   STATUS mandatory
   DESCRIPTION
   "The current summary state of the module."
   ::= { exitShutter 4 }

modCurrentDetailedState OBJECT-TYPE
   SYNTAX INTEGER
   ACCESS read-only
   STATUS mandatory
   DESCRIPTION
   "The status code for the current detailed state."
   ::= { exitShutter 5 }

modCurrentDetailedStateDesc OBJECT-TYPE
   SYNTAX DisplayString
   ACCESS read-only
   STATUS mandatory
   DESCRIPTION
   "A description of the current detailed state."
   ::= { exitShutter 6 }

modPreviousSummaryState OBJECT-TYPE
   SYNTAX ModuleState
   ACCESS read-only
   STATUS mandatory
   DESCRIPTION
   "The previous summary state of the module."
   ::= { exitShutter 7 }

modPreviousDetailedState OBJECT-TYPE
   SYNTAX INTEGER
   ACCESS read-only
   STATUS mandatory
   DESCRIPTION
   "The status code for the previous detailed state."
   ::= { exitShutter 8 }

modPreviousDetailedStateDesc OBJECT-TYPE
   SYNTAX DisplayString
   ACCESS read-only
   STATUS mandatory
   DESCRIPTION
   "A description of the previous detailed state."
   ::= { exitShutter 9 }

modFaultId OBJECT-TYPE
   SYNTAX DisplayString
   ACCESS read-only
   STATUS mandatory
   DESCRIPTION
   "A string of digits summarizing all the information about the current state of the module."
   ::= { exitShutter 10 }

modAssemSerial OBJECT-TYPE
   SYNTAX DisplayString
   ACCESS read-write
   STATUS optional
   DESCRIPTION
   "The serial number of the module."
   ::= { exitShutter 11 }

modAssemAssem OBJECT-TYPE
   SYNTAX DisplayString
   ACCESS read-write
   STATUS optional
   DESCRIPTION
   "The assembly number of the module."
   ::= { exitShutter 12 }

modAssemCode OBJECT-TYPE
   SYNTAX DisplayString
   ACCESS read-write
   STATUS optional
   DESCRIPTION
   "The manufacturing code of the module."
   ::= { exitShutter 13 }

modPMDate OBJECT-TYPE
   SYNTAX DisplayString
   ACCESS read-write
   STATUS optional
   DESCRIPTION
   "Date of the last scheduled service of the module."
   ::= { exitShutter 14 }

modPMData OBJECT-TYPE
   SYNTAX OCTET STRING
   ACCESS read-write
   STATUS optional
   DESCRIPTION
   "Details of the last scheduled service of the module."
   ::= { exitShutter 15 }

-----------------------------------------------------------
-- Device Module Variable Table - exitShutter
-----------------------------------------------------------

modVarTable OBJECT-TYPE
   SYNTAX  SEQUENCE OF ModVarEntry
   ACCESS  not-accessible
   STATUS  mandatory
   DESCRIPTION
   "This group defines the attributes of the variables used by the module to manage its operational state."
   ::= { exitShutter 16 }

modVarEntry OBJECT-TYPE
    SYNTAX      ModVarEntry
    ACCESS      not-accessible
    STATUS      mandatory
    DESCRIPTION "This defines the contents of the table."
    INDEX      {modVarIndex}
    ::= {modVarTable 1}

ModVarEntry ::=
    SEQUENCE   {modVarIndex         INTEGER,
                modVarDesc          DisplayString,
                modVarType          VariableType,
                modVarValue         Counter,
                modVarThreshold1    INTEGER,
                modVarThreshold2    INTEGER}

modVarIndex OBJECT-TYPE
    SYNTAX      INTEGER
    ACCESS      read-only
    STATUS      mandatory
    DESCRIPTION "This is a unique number for every entry in the module 
                 variables table."
    ::= {modVarEntry 1}

modVarDesc OBJECT-TYPE
    SYNTAX      DisplayString
    ACCESS      read-only
    STATUS      mandatory
    DESCRIPTION "A description of the module variable."
    ::= {modVarEntry 2}

modVarType OBJECT-TYPE
    SYNTAX      VariableType
    ACCESS      read-only
    STATUS      mandatory
    DESCRIPTION "An enumerated value indicating whether the variable has
                 thresholds and the type of threshold."
    ::= {modVarEntry 3}

modVarValue OBJECT-TYPE
    SYNTAX      Counter
    ACCESS      read-only
    STATUS      mandatory
    DESCRIPTION "The value of the module variable."
    ::= {modVarEntry 4}

modVarThreshold1 OBJECT-TYPE
    SYNTAX      INTEGER
    ACCESS      read-write
    STATUS      optional
    DESCRIPTION "For variables with one threshold, this is a final value.
                 For variables with two thresholds, this is a warning value."
    ::= {modVarEntry 5}

modVarThreshold2 OBJECT-TYPE
    SYNTAX      INTEGER
    ACCESS      read-write
    STATUS      optional
    DESCRIPTION "For variables with two thresholds, this is the final value."
    ::= {modVarEntry 6}

-------------------------------------------------------------------------------
-- Device Module Actions Table - exitShutter
-----------------------------------------------------------

modActionTable OBJECT-TYPE
   SYNTAX  SEQUENCE OF ModActionEntry
   ACCESS  not-accessible
   STATUS  mandatory
   DESCRIPTION
   "This group defines the attributes of the actions that can be performed on the module to restore or maintain its normal operational state."
   ::= { exitShutter 17 }

modActionEntry OBJECT-TYPE
    SYNTAX      ModActionEntry
    ACCESS      not-accessible
    STATUS      mandatory
    DESCRIPTION "This defines the contents of the table."
    INDEX      {modActionIndex}
    ::= {modActionTable 1}

ModActionEntry ::=
    SEQUENCE   {modActionIndex               INTEGER,
                modActionDesc                DisplayString,
                modActionType                ActionType,
                modActionFaultDetect         TruthValue,
                modActionProactive           TruthValue,
                modActionProactiveDetect     TruthValue,
                modActionCustomerActionable  TruthValue,
                modActionComplete            TruthValue}

modActionIndex OBJECT-TYPE
    SYNTAX      INTEGER
    ACCESS      read-only
    STATUS      mandatory
    DESCRIPTION "A unique number for each action in the module actions table."
    ::= {modActionEntry 1}

modActionDesc OBJECT-TYPE
    SYNTAX      DisplayString
    ACCESS      read-only
    STATUS      mandatory
    DESCRIPTION "A description of the module action."
    ::= {modActionEntry 2}

modActionType OBJECT-TYPE
    SYNTAX      ActionType
    ACCESS      read-only
    STATUS      mandatory
    DESCRIPTION "An enumerated value indicating the type of action performed on
                 the module."
    ::= {modActionEntry 3}

modActionFaultDetect OBJECT-TYPE
    SYNTAX      TruthValue
    ACCESS      read-only
    STATUS      mandatory
    DESCRIPTION "A value of TRUE means the module can automatically detect that
                 the action has been performed for the associated fault that
                 was reported."
    ::= {modActionEntry 4}

modActionProactive OBJECT-TYPE
    SYNTAX      TruthValue
    ACCESS      read-only
    STATUS      mandatory
    DESCRIPTION "A value of TRUE means the action can be performed on the
                 module before the associated fault occurs."
    ::= {modActionEntry 5}

modActionProactiveDetect OBJECT-TYPE
    SYNTAX      TruthValue
    ACCESS      read-only
    STATUS      mandatory
    DESCRIPTION "A value of TRUE means the module can, through its sensors,
                 automatically detect that the action has been performed before
                 the associated fault occurs."
    ::= {modActionEntry 6}

modActionCustomerActionable OBJECT-TYPE
    SYNTAX      TruthValue
    ACCESS      read-only
    STATUS      mandatory
    DESCRIPTION "A value of TRUE means the customer can perform the action."
    ::= {modActionEntry 7}

modActionComplete OBJECT-TYPE
    SYNTAX      TruthValue
    ACCESS      write-only
    STATUS      mandatory
    DESCRIPTION "Setting the value of this attribute to TRUE informs the module
                 that the action has been performed, and clears the appropriate
                 module variables."
    ::= {modActionEntry 8}

END

CASH-01-USBDISPENSER-SUCTIONCUPS-MIB DEFINITIONS ::= BEGIN

--
-- SST CASH-01-USBDISPENSER MIB
--

IMPORTS
    enterprises, Counter
        FROM RFC1155-SMI
    OBJECT-TYPE
        FROM RFC-1212
    DisplayString
        FROM RFC1213-MIB
    TruthValue
        FROM RFC1253-MIB
    sstDevice, VerificationState, ModuleState, VariableType, ActionType
        FROM NCR-CORESST-MIB;

    cash-01-UsbDispenser    OBJECT IDENTIFIER ::= { sstDevice 155 }
    suctionCups              OBJECT IDENTIFIER ::= { cash-01-UsbDispenser 17 }

-------------------------------------------------------------------------------
-- SST Device Module - suctionCups
-----------------------------------------------------------

modIdentifier OBJECT-TYPE
	SYNTAX INTEGER
   ACCESS read-only
   STATUS mandatory
   DESCRIPTION
   "Within the device, this is a unique identifier for the module."
   ::= { suctionCups 1 }

modDesc OBJECT-TYPE
   SYNTAX DisplayString
   ACCESS read-only
   STATUS mandatory
   DESCRIPTION
   "A description of the module."
   ::= { suctionCups 2 }

modReplenishable OBJECT-TYPE
   SYNTAX TruthValue
   ACCESS read-only
   STATUS mandatory
   DESCRIPTION
   "A value of TRUE means the module can be replenished (filled, emptied or renewed).
     A value of FALSE means it can be repaired or replaced."
   ::= { suctionCups 3 }

modCurrentSummaryState OBJECT-TYPE
   SYNTAX ModuleState
   ACCESS read-only
   STATUS mandatory
   DESCRIPTION
   "The current summary state of the module."
   ::= { suctionCups 4 }

modCurrentDetailedState OBJECT-TYPE
   SYNTAX INTEGER
   ACCESS read-only
   STATUS mandatory
   DESCRIPTION
   "The status code for the current detailed state."
   ::= { suctionCups 5 }

modCurrentDetailedStateDesc OBJECT-TYPE
   SYNTAX DisplayString
   ACCESS read-only
   STATUS mandatory
   DESCRIPTION
   "A description of the current detailed state."
   ::= { suctionCups 6 }

modPreviousSummaryState OBJECT-TYPE
   SYNTAX ModuleState
   ACCESS read-only
   STATUS mandatory
   DESCRIPTION
   "The previous summary state of the module."
   ::= { suctionCups 7 }

modPreviousDetailedState OBJECT-TYPE
   SYNTAX INTEGER
   ACCESS read-only
   STATUS mandatory
   DESCRIPTION
   "The status code for the previous detailed state."
   ::= { suctionCups 8 }

modPreviousDetailedStateDesc OBJECT-TYPE
   SYNTAX DisplayString
   ACCESS read-only
   STATUS mandatory
   DESCRIPTION
   "A description of the previous detailed state."
   ::= { suctionCups 9 }

modFaultId OBJECT-TYPE
   SYNTAX DisplayString
   ACCESS read-only
   STATUS mandatory
   DESCRIPTION
   "A string of digits summarizing all the information about the current state of the module."
   ::= { suctionCups 10 }

modAssemSerial OBJECT-TYPE
   SYNTAX DisplayString
   ACCESS read-write
   STATUS optional
   DESCRIPTION
   "The serial number of the module."
   ::= { suctionCups 11 }

modAssemAssem OBJECT-TYPE
   SYNTAX DisplayString
   ACCESS read-write
   STATUS optional
   DESCRIPTION
   "The assembly number of the module."
   ::= { suctionCups 12 }

modAssemCode OBJECT-TYPE
   SYNTAX DisplayString
   ACCESS read-write
   STATUS optional
   DESCRIPTION
   "The manufacturing code of the module."
   ::= { suctionCups 13 }

modPMDate OBJECT-TYPE
   SYNTAX DisplayString
   ACCESS read-write
   STATUS optional
   DESCRIPTION
   "Date of the last scheduled service of the module."
   ::= { suctionCups 14 }

modPMData OBJECT-TYPE
   SYNTAX OCTET STRING
   ACCESS read-write
   STATUS optional
   DESCRIPTION
   "Details of the last scheduled service of the module."
   ::= { suctionCups 15 }

-----------------------------------------------------------
-- Device Module Variable Table - suctionCups
-----------------------------------------------------------

modVarTable OBJECT-TYPE
   SYNTAX  SEQUENCE OF ModVarEntry
   ACCESS  not-accessible
   STATUS  mandatory
   DESCRIPTION
   "This group defines the attributes of the variables used by the module to manage its operational state."
   ::= { suctionCups 16 }

modVarEntry OBJECT-TYPE
    SYNTAX      ModVarEntry
    ACCESS      not-accessible
    STATUS      mandatory
    DESCRIPTION "This defines the contents of the table."
    INDEX      {modVarIndex}
    ::= {modVarTable 1}

ModVarEntry ::=
    SEQUENCE   {modVarIndex         INTEGER,
                modVarDesc          DisplayString,
                modVarType          VariableType,
                modVarValue         Counter,
                modVarThreshold1    INTEGER,
                modVarThreshold2    INTEGER}

modVarIndex OBJECT-TYPE
    SYNTAX      INTEGER
    ACCESS      read-only
    STATUS      mandatory
    DESCRIPTION "This is a unique number for every entry in the module 
                 variables table."
    ::= {modVarEntry 1}

modVarDesc OBJECT-TYPE
    SYNTAX      DisplayString
    ACCESS      read-only
    STATUS      mandatory
    DESCRIPTION "A description of the module variable."
    ::= {modVarEntry 2}

modVarType OBJECT-TYPE
    SYNTAX      VariableType
    ACCESS      read-only
    STATUS      mandatory
    DESCRIPTION "An enumerated value indicating whether the variable has
                 thresholds and the type of threshold."
    ::= {modVarEntry 3}

modVarValue OBJECT-TYPE
    SYNTAX      Counter
    ACCESS      read-only
    STATUS      mandatory
    DESCRIPTION "The value of the module variable."
    ::= {modVarEntry 4}

modVarThreshold1 OBJECT-TYPE
    SYNTAX      INTEGER
    ACCESS      read-write
    STATUS      optional
    DESCRIPTION "For variables with one threshold, this is a final value.
                 For variables with two thresholds, this is a warning value."
    ::= {modVarEntry 5}

modVarThreshold2 OBJECT-TYPE
    SYNTAX      INTEGER
    ACCESS      read-write
    STATUS      optional
    DESCRIPTION "For variables with two thresholds, this is the final value."
    ::= {modVarEntry 6}

-------------------------------------------------------------------------------
-- Device Module Actions Table - suctionCups
-----------------------------------------------------------

modActionTable OBJECT-TYPE
   SYNTAX  SEQUENCE OF ModActionEntry
   ACCESS  not-accessible
   STATUS  mandatory
   DESCRIPTION
   "This group defines the attributes of the actions that can be performed on the module to restore or maintain its normal operational state."
   ::= { suctionCups 17 }

modActionEntry OBJECT-TYPE
    SYNTAX      ModActionEntry
    ACCESS      not-accessible
    STATUS      mandatory
    DESCRIPTION "This defines the contents of the table."
    INDEX      {modActionIndex}
    ::= {modActionTable 1}

ModActionEntry ::=
    SEQUENCE   {modActionIndex               INTEGER,
                modActionDesc                DisplayString,
                modActionType                ActionType,
                modActionFaultDetect         TruthValue,
                modActionProactive           TruthValue,
                modActionProactiveDetect     TruthValue,
                modActionCustomerActionable  TruthValue,
                modActionComplete            TruthValue}

modActionIndex OBJECT-TYPE
    SYNTAX      INTEGER
    ACCESS      read-only
    STATUS      mandatory
    DESCRIPTION "A unique number for each action in the module actions table."
    ::= {modActionEntry 1}

modActionDesc OBJECT-TYPE
    SYNTAX      DisplayString
    ACCESS      read-only
    STATUS      mandatory
    DESCRIPTION "A description of the module action."
    ::= {modActionEntry 2}

modActionType OBJECT-TYPE
    SYNTAX      ActionType
    ACCESS      read-only
    STATUS      mandatory
    DESCRIPTION "An enumerated value indicating the type of action performed on
                 the module."
    ::= {modActionEntry 3}

modActionFaultDetect OBJECT-TYPE
    SYNTAX      TruthValue
    ACCESS      read-only
    STATUS      mandatory
    DESCRIPTION "A value of TRUE means the module can automatically detect that
                 the action has been performed for the associated fault that
                 was reported."
    ::= {modActionEntry 4}

modActionProactive OBJECT-TYPE
    SYNTAX      TruthValue
    ACCESS      read-only
    STATUS      mandatory
    DESCRIPTION "A value of TRUE means the action can be performed on the
                 module before the associated fault occurs."
    ::= {modActionEntry 5}

modActionProactiveDetect OBJECT-TYPE
    SYNTAX      TruthValue
    ACCESS      read-only
    STATUS      mandatory
    DESCRIPTION "A value of TRUE means the module can, through its sensors,
                 automatically detect that the action has been performed before
                 the associated fault occurs."
    ::= {modActionEntry 6}

modActionCustomerActionable OBJECT-TYPE
    SYNTAX      TruthValue
    ACCESS      read-only
    STATUS      mandatory
    DESCRIPTION "A value of TRUE means the customer can perform the action."
    ::= {modActionEntry 7}

modActionComplete OBJECT-TYPE
    SYNTAX      TruthValue
    ACCESS      write-only
    STATUS      mandatory
    DESCRIPTION "Setting the value of this attribute to TRUE informs the module
                 that the action has been performed, and clears the appropriate
                 module variables."
    ::= {modActionEntry 8}

END
