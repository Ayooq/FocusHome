--------------------------------------------------------------------------------
-- Generated by NCR Device MIB Maker, Version 01.02.00
-- Generated on 04/08/2008 18:52:17 +0
--------------------------------------------------------------------------------
-- The content of this document is NCR Intellectual Property and is the property
-- of NCR Financial Solutions Group Ltd.  It is to be treated as strictly
-- confidential and is not to be disclosed, reproduced, or used except as
-- authorised in writing by NCR in connection with the manufacture, maintenance,
-- and use of the NCR equipment to which it pertains.
-- Copyright 2004 NCR Financial Solutions Group Ltd.
--------------------------------------------------------------------------------

RPNT-01-USBTHERMAL-MIB DEFINITIONS ::= BEGIN

--------------------------------------------------------------------------------
-- SST RPNT-01-USBTHERMAL MIB
--------------------------------------------------------------------------------

IMPORTS
    enterprises, Counter
        FROM RFC1155-SMI
    OBJECT-TYPE
        FROM RFC-1212
    DisplayString
        FROM RFC1213-MIB
    TruthValue
        FROM RFC1253-MIB
    sstDevice, VerificationState, ModuleState, VariableType, ActionType
        FROM NCR-CORESST-MIB;

        rpnt-01-UsbThermal    OBJECT IDENTIFIER ::= {sstDevice 138 }
        devObjs OBJECT IDENTIFIER ::= {rpnt-01-UsbThermal 1 }
        srvObjs OBJECT IDENTIFIER ::= {rpnt-01-UsbThermal 4 }

--------------------------------------------------------------------------------
-- Device Service Miscellaneous Definitions
--------------------------------------------------------------------------------
Reset ::= INTEGER {reset   (1)}


--------------------------------------------------------------------------------
-- SST Device - RPNT-01-UsbThermal
-------------------------------------------------------------------------------

devManufacturer OBJECT-TYPE
    SYNTAX      DisplayString
    ACCESS      read-only
    STATUS      optional
    DESCRIPTION "The name of the manufacturer of the product."
    ::= {devObjs 1}

devProduct OBJECT-TYPE
    SYNTAX      DisplayString
    ACCESS      read-only
    STATUS      optional
    DESCRIPTION "This attribute does not apply to SST devices."
    ::= {devObjs 2}

devVersion OBJECT-TYPE
    SYNTAX      DisplayString
    ACCESS      read-only
    STATUS      optional
    DESCRIPTION "This attribute does not apply to SST devices."
    ::= {devObjs 3}

devSerialNo OBJECT-TYPE
    SYNTAX      DisplayString
    ACCESS      read-only
    STATUS      optional
    DESCRIPTION "This attribute does not apply to SST devices."
    ::= {devObjs 4}

devInstallation OBJECT-TYPE
    SYNTAX      DisplayString
    ACCESS      read-only
    STATUS      optional
    DESCRIPTION "The date and time, in DMI-defined format, when the component
                 was (last) installed." 
    ::= {devObjs 5}

devVerify OBJECT-TYPE
    SYNTAX      VerificationState
    ACCESS      read-only
    STATUS      optional
    DESCRIPTION "A level of verification that the device software is installed
                 and functioning. This attribute is not currently supported."
    ::= {devObjs 6}

devName OBJECT-TYPE
    SYNTAX      DisplayString
    ACCESS      read-only
    STATUS      mandatory
    DESCRIPTION "The unique, platform-defined name of the device."
    ::= {devObjs 7}

devShortDesc OBJECT-TYPE
    SYNTAX      DisplayString
    ACCESS      read-only
    STATUS      mandatory
    DESCRIPTION "The platform-defined short description of the device."
    ::= {devObjs 8}

devLongDesc OBJECT-TYPE
    SYNTAX      DisplayString
    ACCESS      read-only
    STATUS      mandatory
    DESCRIPTION "The platform-defined long description of the device."
    ::= {devObjs 9}

devUniversalId OBJECT-TYPE
    SYNTAX      INTEGER
    ACCESS      read-only
    STATUS      mandatory
    DESCRIPTION "The unique, platform-defined identifier for the type of
                 device."
    ::= {devObjs 10}

devVariant OBJECT-TYPE
    SYNTAX      INTEGER
    ACCESS      read-only
    STATUS      mandatory
    DESCRIPTION "The identifier for the specific hardware configuration of the
                 device, indicating what hardware the device has."
    ::= {devObjs 11}

devSummaryState OBJECT-TYPE
    SYNTAX      ModuleState
    ACCESS      read-only
    STATUS      mandatory
    DESCRIPTION "The summary state of the device indicating the state of the
                 device's least healthy module."
    ::= {devObjs 12}

-------------------------------------------------------------------------------
-- SST Service Table
-------------------------------------------------------------------------------

srvServiceTable OBJECT-TYPE
    SYNTAX      SEQUENCE OF SrvServiceEntry
    ACCESS      not-accessible
    STATUS      mandatory
    DESCRIPTION "This group defines the attributes of the services associated
                 with the device.."
    ::= {srvObjs 1}

srvServiceEntry OBJECT-TYPE
    SYNTAX      SrvServiceEntry
    ACCESS      not-accessible
    STATUS      mandatory
    DESCRIPTION "This defines the contents of the table."
    INDEX      {srvServiceIndex}
    ::= {srvServiceTable 1}

SrvServiceEntry ::=
    SEQUENCE   {srvServiceIndex           DisplayString,
                srvServiceVariant         INTEGER,
                srvServiceState           OCTET STRING,
                srvServiceMaintenance     OCTET STRING,
                srvServiceReplenishment   OCTET STRING,
                srvServiceClearState      Reset,
                srvServiceClearTallies    Reset}

srvServiceIndex OBJECT-TYPE
    SYNTAX      DisplayString
    ACCESS      read-only
    STATUS      mandatory
    DESCRIPTION "A unique, platform-defined name for each service."
    ::= {srvServiceEntry 1}

srvServiceVariant OBJECT-TYPE
    SYNTAX      INTEGER
    ACCESS      read-only
    STATUS      mandatory
    DESCRIPTION "The current configuration of the service, indicating the
                 additional transaction facilities available to the transaction
                 application."
    ::= {srvServiceEntry 2}

srvServiceState OBJECT-TYPE
    SYNTAX      OCTET STRING
    ACCESS      read-only
    STATUS      mandatory
    DESCRIPTION "This indicates the current level of availability of the
                 service parts to the transaction application."
    ::= {srvServiceEntry 3}

srvServiceMaintenance OBJECT-TYPE
    SYNTAX      OCTET STRING
    ACCESS      read-only
    STATUS      mandatory
    DESCRIPTION "Maintenance information associated with the last state change
                 in the service: M-Code, M-Status and M-Data."
    ::= {srvServiceEntry 4}

srvServiceReplenishment OBJECT-TYPE
    SYNTAX      OCTET STRING
    ACCESS      read-only
    STATUS      mandatory
    DESCRIPTION "Replenishment status data associated with the last state
                 change in the service: RS-Data."
    ::= {srvServiceEntry 5}

srvServiceClearState OBJECT-TYPE
    SYNTAX      Reset
    ACCESS      write-only
    STATUS      mandatory
    DESCRIPTION "Setting the value of this attribute clears all parts of the
                 service to a good (fully functioning and available) state, but
                 does not guarantee that the fault has been cleared."
    ::= {srvServiceEntry 6}

srvServiceClearTallies OBJECT-TYPE
    SYNTAX      Reset
    ACCESS      write-only
    STATUS      mandatory
    DESCRIPTION "Setting the value of this attribute clears all tallies
                 supported by the service."
    ::= {srvServiceEntry 7}
        

-------------------------------------------------------------------------------
-- SST Service Tallies Table
-------------------------------------------------------------------------------

srvServiceTallyTable OBJECT-TYPE
    SYNTAX      SEQUENCE OF SrvServiceTallyEntry
    ACCESS      not-accessible
    STATUS      mandatory
    DESCRIPTION "This group defines the attributes of the counters supported by
                 the device service to record the operations, usage and
                 performance of the device it manages."
    ::= {srvObjs 2}

srvServiceTallyEntry OBJECT-TYPE
    SYNTAX      SrvServiceTallyEntry
    ACCESS      not-accessible
    STATUS      mandatory
    DESCRIPTION "This defines the contents of the table."
    INDEX      {srvServiceNameIndex, 
                srvServiceTallyIndex}
    ::= {srvServiceTallyTable 1}

SrvServiceTallyEntry ::=
    SEQUENCE   {srvServiceNameIndex     DisplayString,
                srvServiceTallyIndex    INTEGER,
                srvServiceTallyName     DisplayString,
                srvServiceTallyValue    Counter}

srvServiceNameIndex OBJECT-TYPE
    SYNTAX      DisplayString
    ACCESS      read-only
    STATUS      mandatory
    DESCRIPTION "A unique name for each service."
    ::= {srvServiceTallyEntry 1}

srvServiceTallyIndex OBJECT-TYPE
    SYNTAX      INTEGER
    ACCESS      read-only
    STATUS      mandatory
    DESCRIPTION "A unique number for each tally."
    ::= {srvServiceTallyEntry 2}

srvServiceTallyName OBJECT-TYPE
    SYNTAX      DisplayString
    ACCESS      read-only
    STATUS      mandatory
    DESCRIPTION "A description of the tally."
    ::= {srvServiceTallyEntry 3}

srvServiceTallyValue OBJECT-TYPE
    SYNTAX      Counter
    ACCESS      read-only
    STATUS      mandatory
    DESCRIPTION "The current value of the tally."
    ::= {srvServiceTallyEntry 4}
END

RPNT-01-USBTHERMAL-CONTROLBOARD-MIB DEFINITIONS ::= BEGIN

--
-- SST RPNT-01-USBTHERMAL MIB
--

IMPORTS
    enterprises, Counter
        FROM RFC1155-SMI
    OBJECT-TYPE
        FROM RFC-1212
    DisplayString
        FROM RFC1213-MIB
    TruthValue
        FROM RFC1253-MIB
    sstDevice, VerificationState, ModuleState, VariableType, ActionType
        FROM NCR-CORESST-MIB;

    rpnt-01-UsbThermal    OBJECT IDENTIFIER ::= { sstDevice 138 }
    controlBoard              OBJECT IDENTIFIER ::= { rpnt-01-UsbThermal 5 }

-------------------------------------------------------------------------------
-- SST Device Module - controlBoard
-----------------------------------------------------------

modIdentifier OBJECT-TYPE
	SYNTAX INTEGER
   ACCESS read-only
   STATUS mandatory
   DESCRIPTION
   "Within the device, this is a unique identifier for the module."
   ::= { controlBoard 1 }

modDesc OBJECT-TYPE
   SYNTAX DisplayString
   ACCESS read-only
   STATUS mandatory
   DESCRIPTION
   "A description of the module."
   ::= { controlBoard 2 }

modReplenishable OBJECT-TYPE
   SYNTAX TruthValue
   ACCESS read-only
   STATUS mandatory
   DESCRIPTION
   "A value of TRUE means the module can be replenished (filled, emptied or renewed).
     A value of FALSE means it can be repaired or replaced."
   ::= { controlBoard 3 }

modCurrentSummaryState OBJECT-TYPE
   SYNTAX ModuleState
   ACCESS read-only
   STATUS mandatory
   DESCRIPTION
   "The current summary state of the module."
   ::= { controlBoard 4 }

modCurrentDetailedState OBJECT-TYPE
   SYNTAX INTEGER
   ACCESS read-only
   STATUS mandatory
   DESCRIPTION
   "The status code for the current detailed state."
   ::= { controlBoard 5 }

modCurrentDetailedStateDesc OBJECT-TYPE
   SYNTAX DisplayString
   ACCESS read-only
   STATUS mandatory
   DESCRIPTION
   "A description of the current detailed state."
   ::= { controlBoard 6 }

modPreviousSummaryState OBJECT-TYPE
   SYNTAX ModuleState
   ACCESS read-only
   STATUS mandatory
   DESCRIPTION
   "The previous summary state of the module."
   ::= { controlBoard 7 }

modPreviousDetailedState OBJECT-TYPE
   SYNTAX INTEGER
   ACCESS read-only
   STATUS mandatory
   DESCRIPTION
   "The status code for the previous detailed state."
   ::= { controlBoard 8 }

modPreviousDetailedStateDesc OBJECT-TYPE
   SYNTAX DisplayString
   ACCESS read-only
   STATUS mandatory
   DESCRIPTION
   "A description of the previous detailed state."
   ::= { controlBoard 9 }

modFaultId OBJECT-TYPE
   SYNTAX DisplayString
   ACCESS read-only
   STATUS mandatory
   DESCRIPTION
   "A string of digits summarizing all the information about the current state of the module."
   ::= { controlBoard 10 }

modAssemSerial OBJECT-TYPE
   SYNTAX DisplayString
   ACCESS read-write
   STATUS optional
   DESCRIPTION
   "The serial number of the module."
   ::= { controlBoard 11 }

modAssemAssem OBJECT-TYPE
   SYNTAX DisplayString
   ACCESS read-write
   STATUS optional
   DESCRIPTION
   "The assembly number of the module."
   ::= { controlBoard 12 }

modAssemCode OBJECT-TYPE
   SYNTAX DisplayString
   ACCESS read-write
   STATUS optional
   DESCRIPTION
   "The manufacturing code of the module."
   ::= { controlBoard 13 }

modPMDate OBJECT-TYPE
   SYNTAX DisplayString
   ACCESS read-write
   STATUS optional
   DESCRIPTION
   "Date of the last scheduled service of the module."
   ::= { controlBoard 14 }

modPMData OBJECT-TYPE
   SYNTAX OCTET STRING
   ACCESS read-write
   STATUS optional
   DESCRIPTION
   "Details of the last scheduled service of the module."
   ::= { controlBoard 15 }

-----------------------------------------------------------
-- Device Module Variable Table - controlBoard
-----------------------------------------------------------

modVarTable OBJECT-TYPE
   SYNTAX  SEQUENCE OF ModVarEntry
   ACCESS  not-accessible
   STATUS  mandatory
   DESCRIPTION
   "This group defines the attributes of the variables used by the module to manage its operational state."
   ::= { controlBoard 16 }

modVarEntry OBJECT-TYPE
    SYNTAX      ModVarEntry
    ACCESS      not-accessible
    STATUS      mandatory
    DESCRIPTION "This defines the contents of the table."
    INDEX      {modVarIndex}
    ::= {modVarTable 1}

ModVarEntry ::=
    SEQUENCE   {modVarIndex         INTEGER,
                modVarDesc          DisplayString,
                modVarType          VariableType,
                modVarValue         Counter,
                modVarThreshold1    INTEGER,
                modVarThreshold2    INTEGER}

modVarIndex OBJECT-TYPE
    SYNTAX      INTEGER
    ACCESS      read-only
    STATUS      mandatory
    DESCRIPTION "This is a unique number for every entry in the module 
                 variables table."
    ::= {modVarEntry 1}

modVarDesc OBJECT-TYPE
    SYNTAX      DisplayString
    ACCESS      read-only
    STATUS      mandatory
    DESCRIPTION "A description of the module variable."
    ::= {modVarEntry 2}

modVarType OBJECT-TYPE
    SYNTAX      VariableType
    ACCESS      read-only
    STATUS      mandatory
    DESCRIPTION "An enumerated value indicating whether the variable has
                 thresholds and the type of threshold."
    ::= {modVarEntry 3}

modVarValue OBJECT-TYPE
    SYNTAX      Counter
    ACCESS      read-only
    STATUS      mandatory
    DESCRIPTION "The value of the module variable."
    ::= {modVarEntry 4}

modVarThreshold1 OBJECT-TYPE
    SYNTAX      INTEGER
    ACCESS      read-write
    STATUS      optional
    DESCRIPTION "For variables with one threshold, this is a final value.
                 For variables with two thresholds, this is a warning value."
    ::= {modVarEntry 5}

modVarThreshold2 OBJECT-TYPE
    SYNTAX      INTEGER
    ACCESS      read-write
    STATUS      optional
    DESCRIPTION "For variables with two thresholds, this is the final value."
    ::= {modVarEntry 6}

-------------------------------------------------------------------------------
-- Device Module Actions Table - controlBoard
-----------------------------------------------------------

modActionTable OBJECT-TYPE
   SYNTAX  SEQUENCE OF ModActionEntry
   ACCESS  not-accessible
   STATUS  mandatory
   DESCRIPTION
   "This group defines the attributes of the actions that can be performed on the module to restore or maintain its normal operational state."
   ::= { controlBoard 17 }

modActionEntry OBJECT-TYPE
    SYNTAX      ModActionEntry
    ACCESS      not-accessible
    STATUS      mandatory
    DESCRIPTION "This defines the contents of the table."
    INDEX      {modActionIndex}
    ::= {modActionTable 1}

ModActionEntry ::=
    SEQUENCE   {modActionIndex               INTEGER,
                modActionDesc                DisplayString,
                modActionType                ActionType,
                modActionFaultDetect         TruthValue,
                modActionProactive           TruthValue,
                modActionProactiveDetect     TruthValue,
                modActionCustomerActionable  TruthValue,
                modActionComplete            TruthValue}

modActionIndex OBJECT-TYPE
    SYNTAX      INTEGER
    ACCESS      read-only
    STATUS      mandatory
    DESCRIPTION "A unique number for each action in the module actions table."
    ::= {modActionEntry 1}

modActionDesc OBJECT-TYPE
    SYNTAX      DisplayString
    ACCESS      read-only
    STATUS      mandatory
    DESCRIPTION "A description of the module action."
    ::= {modActionEntry 2}

modActionType OBJECT-TYPE
    SYNTAX      ActionType
    ACCESS      read-only
    STATUS      mandatory
    DESCRIPTION "An enumerated value indicating the type of action performed on
                 the module."
    ::= {modActionEntry 3}

modActionFaultDetect OBJECT-TYPE
    SYNTAX      TruthValue
    ACCESS      read-only
    STATUS      mandatory
    DESCRIPTION "A value of TRUE means the module can automatically detect that
                 the action has been performed for the associated fault that
                 was reported."
    ::= {modActionEntry 4}

modActionProactive OBJECT-TYPE
    SYNTAX      TruthValue
    ACCESS      read-only
    STATUS      mandatory
    DESCRIPTION "A value of TRUE means the action can be performed on the
                 module before the associated fault occurs."
    ::= {modActionEntry 5}

modActionProactiveDetect OBJECT-TYPE
    SYNTAX      TruthValue
    ACCESS      read-only
    STATUS      mandatory
    DESCRIPTION "A value of TRUE means the module can, through its sensors,
                 automatically detect that the action has been performed before
                 the associated fault occurs."
    ::= {modActionEntry 6}

modActionCustomerActionable OBJECT-TYPE
    SYNTAX      TruthValue
    ACCESS      read-only
    STATUS      mandatory
    DESCRIPTION "A value of TRUE means the customer can perform the action."
    ::= {modActionEntry 7}

modActionComplete OBJECT-TYPE
    SYNTAX      TruthValue
    ACCESS      write-only
    STATUS      mandatory
    DESCRIPTION "Setting the value of this attribute to TRUE informs the module
                 that the action has been performed, and clears the appropriate
                 module variables."
    ::= {modActionEntry 8}

END

RPNT-01-USBTHERMAL-KNIFE-MIB DEFINITIONS ::= BEGIN

--
-- SST RPNT-01-USBTHERMAL MIB
--

IMPORTS
    enterprises, Counter
        FROM RFC1155-SMI
    OBJECT-TYPE
        FROM RFC-1212
    DisplayString
        FROM RFC1213-MIB
    TruthValue
        FROM RFC1253-MIB
    sstDevice, VerificationState, ModuleState, VariableType, ActionType
        FROM NCR-CORESST-MIB;

    rpnt-01-UsbThermal    OBJECT IDENTIFIER ::= { sstDevice 138 }
    knife              OBJECT IDENTIFIER ::= { rpnt-01-UsbThermal 6 }

-------------------------------------------------------------------------------
-- SST Device Module - knife
-----------------------------------------------------------

modIdentifier OBJECT-TYPE
	SYNTAX INTEGER
   ACCESS read-only
   STATUS mandatory
   DESCRIPTION
   "Within the device, this is a unique identifier for the module."
   ::= { knife 1 }

modDesc OBJECT-TYPE
   SYNTAX DisplayString
   ACCESS read-only
   STATUS mandatory
   DESCRIPTION
   "A description of the module."
   ::= { knife 2 }

modReplenishable OBJECT-TYPE
   SYNTAX TruthValue
   ACCESS read-only
   STATUS mandatory
   DESCRIPTION
   "A value of TRUE means the module can be replenished (filled, emptied or renewed).
     A value of FALSE means it can be repaired or replaced."
   ::= { knife 3 }

modCurrentSummaryState OBJECT-TYPE
   SYNTAX ModuleState
   ACCESS read-only
   STATUS mandatory
   DESCRIPTION
   "The current summary state of the module."
   ::= { knife 4 }

modCurrentDetailedState OBJECT-TYPE
   SYNTAX INTEGER
   ACCESS read-only
   STATUS mandatory
   DESCRIPTION
   "The status code for the current detailed state."
   ::= { knife 5 }

modCurrentDetailedStateDesc OBJECT-TYPE
   SYNTAX DisplayString
   ACCESS read-only
   STATUS mandatory
   DESCRIPTION
   "A description of the current detailed state."
   ::= { knife 6 }

modPreviousSummaryState OBJECT-TYPE
   SYNTAX ModuleState
   ACCESS read-only
   STATUS mandatory
   DESCRIPTION
   "The previous summary state of the module."
   ::= { knife 7 }

modPreviousDetailedState OBJECT-TYPE
   SYNTAX INTEGER
   ACCESS read-only
   STATUS mandatory
   DESCRIPTION
   "The status code for the previous detailed state."
   ::= { knife 8 }

modPreviousDetailedStateDesc OBJECT-TYPE
   SYNTAX DisplayString
   ACCESS read-only
   STATUS mandatory
   DESCRIPTION
   "A description of the previous detailed state."
   ::= { knife 9 }

modFaultId OBJECT-TYPE
   SYNTAX DisplayString
   ACCESS read-only
   STATUS mandatory
   DESCRIPTION
   "A string of digits summarizing all the information about the current state of the module."
   ::= { knife 10 }

modAssemSerial OBJECT-TYPE
   SYNTAX DisplayString
   ACCESS read-write
   STATUS optional
   DESCRIPTION
   "The serial number of the module."
   ::= { knife 11 }

modAssemAssem OBJECT-TYPE
   SYNTAX DisplayString
   ACCESS read-write
   STATUS optional
   DESCRIPTION
   "The assembly number of the module."
   ::= { knife 12 }

modAssemCode OBJECT-TYPE
   SYNTAX DisplayString
   ACCESS read-write
   STATUS optional
   DESCRIPTION
   "The manufacturing code of the module."
   ::= { knife 13 }

modPMDate OBJECT-TYPE
   SYNTAX DisplayString
   ACCESS read-write
   STATUS optional
   DESCRIPTION
   "Date of the last scheduled service of the module."
   ::= { knife 14 }

modPMData OBJECT-TYPE
   SYNTAX OCTET STRING
   ACCESS read-write
   STATUS optional
   DESCRIPTION
   "Details of the last scheduled service of the module."
   ::= { knife 15 }

-----------------------------------------------------------
-- Device Module Variable Table - knife
-----------------------------------------------------------

modVarTable OBJECT-TYPE
   SYNTAX  SEQUENCE OF ModVarEntry
   ACCESS  not-accessible
   STATUS  mandatory
   DESCRIPTION
   "This group defines the attributes of the variables used by the module to manage its operational state."
   ::= { knife 16 }

modVarEntry OBJECT-TYPE
    SYNTAX      ModVarEntry
    ACCESS      not-accessible
    STATUS      mandatory
    DESCRIPTION "This defines the contents of the table."
    INDEX      {modVarIndex}
    ::= {modVarTable 1}

ModVarEntry ::=
    SEQUENCE   {modVarIndex         INTEGER,
                modVarDesc          DisplayString,
                modVarType          VariableType,
                modVarValue         Counter,
                modVarThreshold1    INTEGER,
                modVarThreshold2    INTEGER}

modVarIndex OBJECT-TYPE
    SYNTAX      INTEGER
    ACCESS      read-only
    STATUS      mandatory
    DESCRIPTION "This is a unique number for every entry in the module 
                 variables table."
    ::= {modVarEntry 1}

modVarDesc OBJECT-TYPE
    SYNTAX      DisplayString
    ACCESS      read-only
    STATUS      mandatory
    DESCRIPTION "A description of the module variable."
    ::= {modVarEntry 2}

modVarType OBJECT-TYPE
    SYNTAX      VariableType
    ACCESS      read-only
    STATUS      mandatory
    DESCRIPTION "An enumerated value indicating whether the variable has
                 thresholds and the type of threshold."
    ::= {modVarEntry 3}

modVarValue OBJECT-TYPE
    SYNTAX      Counter
    ACCESS      read-only
    STATUS      mandatory
    DESCRIPTION "The value of the module variable."
    ::= {modVarEntry 4}

modVarThreshold1 OBJECT-TYPE
    SYNTAX      INTEGER
    ACCESS      read-write
    STATUS      optional
    DESCRIPTION "For variables with one threshold, this is a final value.
                 For variables with two thresholds, this is a warning value."
    ::= {modVarEntry 5}

modVarThreshold2 OBJECT-TYPE
    SYNTAX      INTEGER
    ACCESS      read-write
    STATUS      optional
    DESCRIPTION "For variables with two thresholds, this is the final value."
    ::= {modVarEntry 6}

-------------------------------------------------------------------------------
-- Device Module Actions Table - knife
-----------------------------------------------------------

modActionTable OBJECT-TYPE
   SYNTAX  SEQUENCE OF ModActionEntry
   ACCESS  not-accessible
   STATUS  mandatory
   DESCRIPTION
   "This group defines the attributes of the actions that can be performed on the module to restore or maintain its normal operational state."
   ::= { knife 17 }

modActionEntry OBJECT-TYPE
    SYNTAX      ModActionEntry
    ACCESS      not-accessible
    STATUS      mandatory
    DESCRIPTION "This defines the contents of the table."
    INDEX      {modActionIndex}
    ::= {modActionTable 1}

ModActionEntry ::=
    SEQUENCE   {modActionIndex               INTEGER,
                modActionDesc                DisplayString,
                modActionType                ActionType,
                modActionFaultDetect         TruthValue,
                modActionProactive           TruthValue,
                modActionProactiveDetect     TruthValue,
                modActionCustomerActionable  TruthValue,
                modActionComplete            TruthValue}

modActionIndex OBJECT-TYPE
    SYNTAX      INTEGER
    ACCESS      read-only
    STATUS      mandatory
    DESCRIPTION "A unique number for each action in the module actions table."
    ::= {modActionEntry 1}

modActionDesc OBJECT-TYPE
    SYNTAX      DisplayString
    ACCESS      read-only
    STATUS      mandatory
    DESCRIPTION "A description of the module action."
    ::= {modActionEntry 2}

modActionType OBJECT-TYPE
    SYNTAX      ActionType
    ACCESS      read-only
    STATUS      mandatory
    DESCRIPTION "An enumerated value indicating the type of action performed on
                 the module."
    ::= {modActionEntry 3}

modActionFaultDetect OBJECT-TYPE
    SYNTAX      TruthValue
    ACCESS      read-only
    STATUS      mandatory
    DESCRIPTION "A value of TRUE means the module can automatically detect that
                 the action has been performed for the associated fault that
                 was reported."
    ::= {modActionEntry 4}

modActionProactive OBJECT-TYPE
    SYNTAX      TruthValue
    ACCESS      read-only
    STATUS      mandatory
    DESCRIPTION "A value of TRUE means the action can be performed on the
                 module before the associated fault occurs."
    ::= {modActionEntry 5}

modActionProactiveDetect OBJECT-TYPE
    SYNTAX      TruthValue
    ACCESS      read-only
    STATUS      mandatory
    DESCRIPTION "A value of TRUE means the module can, through its sensors,
                 automatically detect that the action has been performed before
                 the associated fault occurs."
    ::= {modActionEntry 6}

modActionCustomerActionable OBJECT-TYPE
    SYNTAX      TruthValue
    ACCESS      read-only
    STATUS      mandatory
    DESCRIPTION "A value of TRUE means the customer can perform the action."
    ::= {modActionEntry 7}

modActionComplete OBJECT-TYPE
    SYNTAX      TruthValue
    ACCESS      write-only
    STATUS      mandatory
    DESCRIPTION "Setting the value of this attribute to TRUE informs the module
                 that the action has been performed, and clears the appropriate
                 module variables."
    ::= {modActionEntry 8}

END

RPNT-01-USBTHERMAL-PRINTHEAD-MIB DEFINITIONS ::= BEGIN

--
-- SST RPNT-01-USBTHERMAL MIB
--

IMPORTS
    enterprises, Counter
        FROM RFC1155-SMI
    OBJECT-TYPE
        FROM RFC-1212
    DisplayString
        FROM RFC1213-MIB
    TruthValue
        FROM RFC1253-MIB
    sstDevice, VerificationState, ModuleState, VariableType, ActionType
        FROM NCR-CORESST-MIB;

    rpnt-01-UsbThermal    OBJECT IDENTIFIER ::= { sstDevice 138 }
    printHead              OBJECT IDENTIFIER ::= { rpnt-01-UsbThermal 7 }

-------------------------------------------------------------------------------
-- SST Device Module - printHead
-----------------------------------------------------------

modIdentifier OBJECT-TYPE
	SYNTAX INTEGER
   ACCESS read-only
   STATUS mandatory
   DESCRIPTION
   "Within the device, this is a unique identifier for the module."
   ::= { printHead 1 }

modDesc OBJECT-TYPE
   SYNTAX DisplayString
   ACCESS read-only
   STATUS mandatory
   DESCRIPTION
   "A description of the module."
   ::= { printHead 2 }

modReplenishable OBJECT-TYPE
   SYNTAX TruthValue
   ACCESS read-only
   STATUS mandatory
   DESCRIPTION
   "A value of TRUE means the module can be replenished (filled, emptied or renewed).
     A value of FALSE means it can be repaired or replaced."
   ::= { printHead 3 }

modCurrentSummaryState OBJECT-TYPE
   SYNTAX ModuleState
   ACCESS read-only
   STATUS mandatory
   DESCRIPTION
   "The current summary state of the module."
   ::= { printHead 4 }

modCurrentDetailedState OBJECT-TYPE
   SYNTAX INTEGER
   ACCESS read-only
   STATUS mandatory
   DESCRIPTION
   "The status code for the current detailed state."
   ::= { printHead 5 }

modCurrentDetailedStateDesc OBJECT-TYPE
   SYNTAX DisplayString
   ACCESS read-only
   STATUS mandatory
   DESCRIPTION
   "A description of the current detailed state."
   ::= { printHead 6 }

modPreviousSummaryState OBJECT-TYPE
   SYNTAX ModuleState
   ACCESS read-only
   STATUS mandatory
   DESCRIPTION
   "The previous summary state of the module."
   ::= { printHead 7 }

modPreviousDetailedState OBJECT-TYPE
   SYNTAX INTEGER
   ACCESS read-only
   STATUS mandatory
   DESCRIPTION
   "The status code for the previous detailed state."
   ::= { printHead 8 }

modPreviousDetailedStateDesc OBJECT-TYPE
   SYNTAX DisplayString
   ACCESS read-only
   STATUS mandatory
   DESCRIPTION
   "A description of the previous detailed state."
   ::= { printHead 9 }

modFaultId OBJECT-TYPE
   SYNTAX DisplayString
   ACCESS read-only
   STATUS mandatory
   DESCRIPTION
   "A string of digits summarizing all the information about the current state of the module."
   ::= { printHead 10 }

modAssemSerial OBJECT-TYPE
   SYNTAX DisplayString
   ACCESS read-write
   STATUS optional
   DESCRIPTION
   "The serial number of the module."
   ::= { printHead 11 }

modAssemAssem OBJECT-TYPE
   SYNTAX DisplayString
   ACCESS read-write
   STATUS optional
   DESCRIPTION
   "The assembly number of the module."
   ::= { printHead 12 }

modAssemCode OBJECT-TYPE
   SYNTAX DisplayString
   ACCESS read-write
   STATUS optional
   DESCRIPTION
   "The manufacturing code of the module."
   ::= { printHead 13 }

modPMDate OBJECT-TYPE
   SYNTAX DisplayString
   ACCESS read-write
   STATUS optional
   DESCRIPTION
   "Date of the last scheduled service of the module."
   ::= { printHead 14 }

modPMData OBJECT-TYPE
   SYNTAX OCTET STRING
   ACCESS read-write
   STATUS optional
   DESCRIPTION
   "Details of the last scheduled service of the module."
   ::= { printHead 15 }

-----------------------------------------------------------
-- Device Module Variable Table - printHead
-----------------------------------------------------------

modVarTable OBJECT-TYPE
   SYNTAX  SEQUENCE OF ModVarEntry
   ACCESS  not-accessible
   STATUS  mandatory
   DESCRIPTION
   "This group defines the attributes of the variables used by the module to manage its operational state."
   ::= { printHead 16 }

modVarEntry OBJECT-TYPE
    SYNTAX      ModVarEntry
    ACCESS      not-accessible
    STATUS      mandatory
    DESCRIPTION "This defines the contents of the table."
    INDEX      {modVarIndex}
    ::= {modVarTable 1}

ModVarEntry ::=
    SEQUENCE   {modVarIndex         INTEGER,
                modVarDesc          DisplayString,
                modVarType          VariableType,
                modVarValue         Counter,
                modVarThreshold1    INTEGER,
                modVarThreshold2    INTEGER}

modVarIndex OBJECT-TYPE
    SYNTAX      INTEGER
    ACCESS      read-only
    STATUS      mandatory
    DESCRIPTION "This is a unique number for every entry in the module 
                 variables table."
    ::= {modVarEntry 1}

modVarDesc OBJECT-TYPE
    SYNTAX      DisplayString
    ACCESS      read-only
    STATUS      mandatory
    DESCRIPTION "A description of the module variable."
    ::= {modVarEntry 2}

modVarType OBJECT-TYPE
    SYNTAX      VariableType
    ACCESS      read-only
    STATUS      mandatory
    DESCRIPTION "An enumerated value indicating whether the variable has
                 thresholds and the type of threshold."
    ::= {modVarEntry 3}

modVarValue OBJECT-TYPE
    SYNTAX      Counter
    ACCESS      read-only
    STATUS      mandatory
    DESCRIPTION "The value of the module variable."
    ::= {modVarEntry 4}

modVarThreshold1 OBJECT-TYPE
    SYNTAX      INTEGER
    ACCESS      read-write
    STATUS      optional
    DESCRIPTION "For variables with one threshold, this is a final value.
                 For variables with two thresholds, this is a warning value."
    ::= {modVarEntry 5}

modVarThreshold2 OBJECT-TYPE
    SYNTAX      INTEGER
    ACCESS      read-write
    STATUS      optional
    DESCRIPTION "For variables with two thresholds, this is the final value."
    ::= {modVarEntry 6}

-------------------------------------------------------------------------------
-- Device Module Actions Table - printHead
-----------------------------------------------------------

modActionTable OBJECT-TYPE
   SYNTAX  SEQUENCE OF ModActionEntry
   ACCESS  not-accessible
   STATUS  mandatory
   DESCRIPTION
   "This group defines the attributes of the actions that can be performed on the module to restore or maintain its normal operational state."
   ::= { printHead 17 }

modActionEntry OBJECT-TYPE
    SYNTAX      ModActionEntry
    ACCESS      not-accessible
    STATUS      mandatory
    DESCRIPTION "This defines the contents of the table."
    INDEX      {modActionIndex}
    ::= {modActionTable 1}

ModActionEntry ::=
    SEQUENCE   {modActionIndex               INTEGER,
                modActionDesc                DisplayString,
                modActionType                ActionType,
                modActionFaultDetect         TruthValue,
                modActionProactive           TruthValue,
                modActionProactiveDetect     TruthValue,
                modActionCustomerActionable  TruthValue,
                modActionComplete            TruthValue}

modActionIndex OBJECT-TYPE
    SYNTAX      INTEGER
    ACCESS      read-only
    STATUS      mandatory
    DESCRIPTION "A unique number for each action in the module actions table."
    ::= {modActionEntry 1}

modActionDesc OBJECT-TYPE
    SYNTAX      DisplayString
    ACCESS      read-only
    STATUS      mandatory
    DESCRIPTION "A description of the module action."
    ::= {modActionEntry 2}

modActionType OBJECT-TYPE
    SYNTAX      ActionType
    ACCESS      read-only
    STATUS      mandatory
    DESCRIPTION "An enumerated value indicating the type of action performed on
                 the module."
    ::= {modActionEntry 3}

modActionFaultDetect OBJECT-TYPE
    SYNTAX      TruthValue
    ACCESS      read-only
    STATUS      mandatory
    DESCRIPTION "A value of TRUE means the module can automatically detect that
                 the action has been performed for the associated fault that
                 was reported."
    ::= {modActionEntry 4}

modActionProactive OBJECT-TYPE
    SYNTAX      TruthValue
    ACCESS      read-only
    STATUS      mandatory
    DESCRIPTION "A value of TRUE means the action can be performed on the
                 module before the associated fault occurs."
    ::= {modActionEntry 5}

modActionProactiveDetect OBJECT-TYPE
    SYNTAX      TruthValue
    ACCESS      read-only
    STATUS      mandatory
    DESCRIPTION "A value of TRUE means the module can, through its sensors,
                 automatically detect that the action has been performed before
                 the associated fault occurs."
    ::= {modActionEntry 6}

modActionCustomerActionable OBJECT-TYPE
    SYNTAX      TruthValue
    ACCESS      read-only
    STATUS      mandatory
    DESCRIPTION "A value of TRUE means the customer can perform the action."
    ::= {modActionEntry 7}

modActionComplete OBJECT-TYPE
    SYNTAX      TruthValue
    ACCESS      write-only
    STATUS      mandatory
    DESCRIPTION "Setting the value of this attribute to TRUE informs the module
                 that the action has been performed, and clears the appropriate
                 module variables."
    ::= {modActionEntry 8}

END

RPNT-01-USBTHERMAL-MECHANISM-MIB DEFINITIONS ::= BEGIN

--
-- SST RPNT-01-USBTHERMAL MIB
--

IMPORTS
    enterprises, Counter
        FROM RFC1155-SMI
    OBJECT-TYPE
        FROM RFC-1212
    DisplayString
        FROM RFC1213-MIB
    TruthValue
        FROM RFC1253-MIB
    sstDevice, VerificationState, ModuleState, VariableType, ActionType
        FROM NCR-CORESST-MIB;

    rpnt-01-UsbThermal    OBJECT IDENTIFIER ::= { sstDevice 138 }
    mechanism              OBJECT IDENTIFIER ::= { rpnt-01-UsbThermal 8 }

-------------------------------------------------------------------------------
-- SST Device Module - mechanism
-----------------------------------------------------------

modIdentifier OBJECT-TYPE
	SYNTAX INTEGER
   ACCESS read-only
   STATUS mandatory
   DESCRIPTION
   "Within the device, this is a unique identifier for the module."
   ::= { mechanism 1 }

modDesc OBJECT-TYPE
   SYNTAX DisplayString
   ACCESS read-only
   STATUS mandatory
   DESCRIPTION
   "A description of the module."
   ::= { mechanism 2 }

modReplenishable OBJECT-TYPE
   SYNTAX TruthValue
   ACCESS read-only
   STATUS mandatory
   DESCRIPTION
   "A value of TRUE means the module can be replenished (filled, emptied or renewed).
     A value of FALSE means it can be repaired or replaced."
   ::= { mechanism 3 }

modCurrentSummaryState OBJECT-TYPE
   SYNTAX ModuleState
   ACCESS read-only
   STATUS mandatory
   DESCRIPTION
   "The current summary state of the module."
   ::= { mechanism 4 }

modCurrentDetailedState OBJECT-TYPE
   SYNTAX INTEGER
   ACCESS read-only
   STATUS mandatory
   DESCRIPTION
   "The status code for the current detailed state."
   ::= { mechanism 5 }

modCurrentDetailedStateDesc OBJECT-TYPE
   SYNTAX DisplayString
   ACCESS read-only
   STATUS mandatory
   DESCRIPTION
   "A description of the current detailed state."
   ::= { mechanism 6 }

modPreviousSummaryState OBJECT-TYPE
   SYNTAX ModuleState
   ACCESS read-only
   STATUS mandatory
   DESCRIPTION
   "The previous summary state of the module."
   ::= { mechanism 7 }

modPreviousDetailedState OBJECT-TYPE
   SYNTAX INTEGER
   ACCESS read-only
   STATUS mandatory
   DESCRIPTION
   "The status code for the previous detailed state."
   ::= { mechanism 8 }

modPreviousDetailedStateDesc OBJECT-TYPE
   SYNTAX DisplayString
   ACCESS read-only
   STATUS mandatory
   DESCRIPTION
   "A description of the previous detailed state."
   ::= { mechanism 9 }

modFaultId OBJECT-TYPE
   SYNTAX DisplayString
   ACCESS read-only
   STATUS mandatory
   DESCRIPTION
   "A string of digits summarizing all the information about the current state of the module."
   ::= { mechanism 10 }

modAssemSerial OBJECT-TYPE
   SYNTAX DisplayString
   ACCESS read-write
   STATUS optional
   DESCRIPTION
   "The serial number of the module."
   ::= { mechanism 11 }

modAssemAssem OBJECT-TYPE
   SYNTAX DisplayString
   ACCESS read-write
   STATUS optional
   DESCRIPTION
   "The assembly number of the module."
   ::= { mechanism 12 }

modAssemCode OBJECT-TYPE
   SYNTAX DisplayString
   ACCESS read-write
   STATUS optional
   DESCRIPTION
   "The manufacturing code of the module."
   ::= { mechanism 13 }

modPMDate OBJECT-TYPE
   SYNTAX DisplayString
   ACCESS read-write
   STATUS optional
   DESCRIPTION
   "Date of the last scheduled service of the module."
   ::= { mechanism 14 }

modPMData OBJECT-TYPE
   SYNTAX OCTET STRING
   ACCESS read-write
   STATUS optional
   DESCRIPTION
   "Details of the last scheduled service of the module."
   ::= { mechanism 15 }

-----------------------------------------------------------
-- Device Module Variable Table - mechanism
-----------------------------------------------------------

modVarTable OBJECT-TYPE
   SYNTAX  SEQUENCE OF ModVarEntry
   ACCESS  not-accessible
   STATUS  mandatory
   DESCRIPTION
   "This group defines the attributes of the variables used by the module to manage its operational state."
   ::= { mechanism 16 }

modVarEntry OBJECT-TYPE
    SYNTAX      ModVarEntry
    ACCESS      not-accessible
    STATUS      mandatory
    DESCRIPTION "This defines the contents of the table."
    INDEX      {modVarIndex}
    ::= {modVarTable 1}

ModVarEntry ::=
    SEQUENCE   {modVarIndex         INTEGER,
                modVarDesc          DisplayString,
                modVarType          VariableType,
                modVarValue         Counter,
                modVarThreshold1    INTEGER,
                modVarThreshold2    INTEGER}

modVarIndex OBJECT-TYPE
    SYNTAX      INTEGER
    ACCESS      read-only
    STATUS      mandatory
    DESCRIPTION "This is a unique number for every entry in the module 
                 variables table."
    ::= {modVarEntry 1}

modVarDesc OBJECT-TYPE
    SYNTAX      DisplayString
    ACCESS      read-only
    STATUS      mandatory
    DESCRIPTION "A description of the module variable."
    ::= {modVarEntry 2}

modVarType OBJECT-TYPE
    SYNTAX      VariableType
    ACCESS      read-only
    STATUS      mandatory
    DESCRIPTION "An enumerated value indicating whether the variable has
                 thresholds and the type of threshold."
    ::= {modVarEntry 3}

modVarValue OBJECT-TYPE
    SYNTAX      Counter
    ACCESS      read-only
    STATUS      mandatory
    DESCRIPTION "The value of the module variable."
    ::= {modVarEntry 4}

modVarThreshold1 OBJECT-TYPE
    SYNTAX      INTEGER
    ACCESS      read-write
    STATUS      optional
    DESCRIPTION "For variables with one threshold, this is a final value.
                 For variables with two thresholds, this is a warning value."
    ::= {modVarEntry 5}

modVarThreshold2 OBJECT-TYPE
    SYNTAX      INTEGER
    ACCESS      read-write
    STATUS      optional
    DESCRIPTION "For variables with two thresholds, this is the final value."
    ::= {modVarEntry 6}

-------------------------------------------------------------------------------
-- Device Module Actions Table - mechanism
-----------------------------------------------------------

modActionTable OBJECT-TYPE
   SYNTAX  SEQUENCE OF ModActionEntry
   ACCESS  not-accessible
   STATUS  mandatory
   DESCRIPTION
   "This group defines the attributes of the actions that can be performed on the module to restore or maintain its normal operational state."
   ::= { mechanism 17 }

modActionEntry OBJECT-TYPE
    SYNTAX      ModActionEntry
    ACCESS      not-accessible
    STATUS      mandatory
    DESCRIPTION "This defines the contents of the table."
    INDEX      {modActionIndex}
    ::= {modActionTable 1}

ModActionEntry ::=
    SEQUENCE   {modActionIndex               INTEGER,
                modActionDesc                DisplayString,
                modActionType                ActionType,
                modActionFaultDetect         TruthValue,
                modActionProactive           TruthValue,
                modActionProactiveDetect     TruthValue,
                modActionCustomerActionable  TruthValue,
                modActionComplete            TruthValue}

modActionIndex OBJECT-TYPE
    SYNTAX      INTEGER
    ACCESS      read-only
    STATUS      mandatory
    DESCRIPTION "A unique number for each action in the module actions table."
    ::= {modActionEntry 1}

modActionDesc OBJECT-TYPE
    SYNTAX      DisplayString
    ACCESS      read-only
    STATUS      mandatory
    DESCRIPTION "A description of the module action."
    ::= {modActionEntry 2}

modActionType OBJECT-TYPE
    SYNTAX      ActionType
    ACCESS      read-only
    STATUS      mandatory
    DESCRIPTION "An enumerated value indicating the type of action performed on
                 the module."
    ::= {modActionEntry 3}

modActionFaultDetect OBJECT-TYPE
    SYNTAX      TruthValue
    ACCESS      read-only
    STATUS      mandatory
    DESCRIPTION "A value of TRUE means the module can automatically detect that
                 the action has been performed for the associated fault that
                 was reported."
    ::= {modActionEntry 4}

modActionProactive OBJECT-TYPE
    SYNTAX      TruthValue
    ACCESS      read-only
    STATUS      mandatory
    DESCRIPTION "A value of TRUE means the action can be performed on the
                 module before the associated fault occurs."
    ::= {modActionEntry 5}

modActionProactiveDetect OBJECT-TYPE
    SYNTAX      TruthValue
    ACCESS      read-only
    STATUS      mandatory
    DESCRIPTION "A value of TRUE means the module can, through its sensors,
                 automatically detect that the action has been performed before
                 the associated fault occurs."
    ::= {modActionEntry 6}

modActionCustomerActionable OBJECT-TYPE
    SYNTAX      TruthValue
    ACCESS      read-only
    STATUS      mandatory
    DESCRIPTION "A value of TRUE means the customer can perform the action."
    ::= {modActionEntry 7}

modActionComplete OBJECT-TYPE
    SYNTAX      TruthValue
    ACCESS      write-only
    STATUS      mandatory
    DESCRIPTION "Setting the value of this attribute to TRUE informs the module
                 that the action has been performed, and clears the appropriate
                 module variables."
    ::= {modActionEntry 8}

END

RPNT-01-USBTHERMAL-TRANSPORT-MIB DEFINITIONS ::= BEGIN

--
-- SST RPNT-01-USBTHERMAL MIB
--

IMPORTS
    enterprises, Counter
        FROM RFC1155-SMI
    OBJECT-TYPE
        FROM RFC-1212
    DisplayString
        FROM RFC1213-MIB
    TruthValue
        FROM RFC1253-MIB
    sstDevice, VerificationState, ModuleState, VariableType, ActionType
        FROM NCR-CORESST-MIB;

    rpnt-01-UsbThermal    OBJECT IDENTIFIER ::= { sstDevice 138 }
    transport              OBJECT IDENTIFIER ::= { rpnt-01-UsbThermal 9 }

-------------------------------------------------------------------------------
-- SST Device Module - transport
-----------------------------------------------------------

modIdentifier OBJECT-TYPE
	SYNTAX INTEGER
   ACCESS read-only
   STATUS mandatory
   DESCRIPTION
   "Within the device, this is a unique identifier for the module."
   ::= { transport 1 }

modDesc OBJECT-TYPE
   SYNTAX DisplayString
   ACCESS read-only
   STATUS mandatory
   DESCRIPTION
   "A description of the module."
   ::= { transport 2 }

modReplenishable OBJECT-TYPE
   SYNTAX TruthValue
   ACCESS read-only
   STATUS mandatory
   DESCRIPTION
   "A value of TRUE means the module can be replenished (filled, emptied or renewed).
     A value of FALSE means it can be repaired or replaced."
   ::= { transport 3 }

modCurrentSummaryState OBJECT-TYPE
   SYNTAX ModuleState
   ACCESS read-only
   STATUS mandatory
   DESCRIPTION
   "The current summary state of the module."
   ::= { transport 4 }

modCurrentDetailedState OBJECT-TYPE
   SYNTAX INTEGER
   ACCESS read-only
   STATUS mandatory
   DESCRIPTION
   "The status code for the current detailed state."
   ::= { transport 5 }

modCurrentDetailedStateDesc OBJECT-TYPE
   SYNTAX DisplayString
   ACCESS read-only
   STATUS mandatory
   DESCRIPTION
   "A description of the current detailed state."
   ::= { transport 6 }

modPreviousSummaryState OBJECT-TYPE
   SYNTAX ModuleState
   ACCESS read-only
   STATUS mandatory
   DESCRIPTION
   "The previous summary state of the module."
   ::= { transport 7 }

modPreviousDetailedState OBJECT-TYPE
   SYNTAX INTEGER
   ACCESS read-only
   STATUS mandatory
   DESCRIPTION
   "The status code for the previous detailed state."
   ::= { transport 8 }

modPreviousDetailedStateDesc OBJECT-TYPE
   SYNTAX DisplayString
   ACCESS read-only
   STATUS mandatory
   DESCRIPTION
   "A description of the previous detailed state."
   ::= { transport 9 }

modFaultId OBJECT-TYPE
   SYNTAX DisplayString
   ACCESS read-only
   STATUS mandatory
   DESCRIPTION
   "A string of digits summarizing all the information about the current state of the module."
   ::= { transport 10 }

modAssemSerial OBJECT-TYPE
   SYNTAX DisplayString
   ACCESS read-write
   STATUS optional
   DESCRIPTION
   "The serial number of the module."
   ::= { transport 11 }

modAssemAssem OBJECT-TYPE
   SYNTAX DisplayString
   ACCESS read-write
   STATUS optional
   DESCRIPTION
   "The assembly number of the module."
   ::= { transport 12 }

modAssemCode OBJECT-TYPE
   SYNTAX DisplayString
   ACCESS read-write
   STATUS optional
   DESCRIPTION
   "The manufacturing code of the module."
   ::= { transport 13 }

modPMDate OBJECT-TYPE
   SYNTAX DisplayString
   ACCESS read-write
   STATUS optional
   DESCRIPTION
   "Date of the last scheduled service of the module."
   ::= { transport 14 }

modPMData OBJECT-TYPE
   SYNTAX OCTET STRING
   ACCESS read-write
   STATUS optional
   DESCRIPTION
   "Details of the last scheduled service of the module."
   ::= { transport 15 }

-----------------------------------------------------------
-- Device Module Variable Table - transport
-----------------------------------------------------------

modVarTable OBJECT-TYPE
   SYNTAX  SEQUENCE OF ModVarEntry
   ACCESS  not-accessible
   STATUS  mandatory
   DESCRIPTION
   "This group defines the attributes of the variables used by the module to manage its operational state."
   ::= { transport 16 }

modVarEntry OBJECT-TYPE
    SYNTAX      ModVarEntry
    ACCESS      not-accessible
    STATUS      mandatory
    DESCRIPTION "This defines the contents of the table."
    INDEX      {modVarIndex}
    ::= {modVarTable 1}

ModVarEntry ::=
    SEQUENCE   {modVarIndex         INTEGER,
                modVarDesc          DisplayString,
                modVarType          VariableType,
                modVarValue         Counter,
                modVarThreshold1    INTEGER,
                modVarThreshold2    INTEGER}

modVarIndex OBJECT-TYPE
    SYNTAX      INTEGER
    ACCESS      read-only
    STATUS      mandatory
    DESCRIPTION "This is a unique number for every entry in the module 
                 variables table."
    ::= {modVarEntry 1}

modVarDesc OBJECT-TYPE
    SYNTAX      DisplayString
    ACCESS      read-only
    STATUS      mandatory
    DESCRIPTION "A description of the module variable."
    ::= {modVarEntry 2}

modVarType OBJECT-TYPE
    SYNTAX      VariableType
    ACCESS      read-only
    STATUS      mandatory
    DESCRIPTION "An enumerated value indicating whether the variable has
                 thresholds and the type of threshold."
    ::= {modVarEntry 3}

modVarValue OBJECT-TYPE
    SYNTAX      Counter
    ACCESS      read-only
    STATUS      mandatory
    DESCRIPTION "The value of the module variable."
    ::= {modVarEntry 4}

modVarThreshold1 OBJECT-TYPE
    SYNTAX      INTEGER
    ACCESS      read-write
    STATUS      optional
    DESCRIPTION "For variables with one threshold, this is a final value.
                 For variables with two thresholds, this is a warning value."
    ::= {modVarEntry 5}

modVarThreshold2 OBJECT-TYPE
    SYNTAX      INTEGER
    ACCESS      read-write
    STATUS      optional
    DESCRIPTION "For variables with two thresholds, this is the final value."
    ::= {modVarEntry 6}

-------------------------------------------------------------------------------
-- Device Module Actions Table - transport
-----------------------------------------------------------

modActionTable OBJECT-TYPE
   SYNTAX  SEQUENCE OF ModActionEntry
   ACCESS  not-accessible
   STATUS  mandatory
   DESCRIPTION
   "This group defines the attributes of the actions that can be performed on the module to restore or maintain its normal operational state."
   ::= { transport 17 }

modActionEntry OBJECT-TYPE
    SYNTAX      ModActionEntry
    ACCESS      not-accessible
    STATUS      mandatory
    DESCRIPTION "This defines the contents of the table."
    INDEX      {modActionIndex}
    ::= {modActionTable 1}

ModActionEntry ::=
    SEQUENCE   {modActionIndex               INTEGER,
                modActionDesc                DisplayString,
                modActionType                ActionType,
                modActionFaultDetect         TruthValue,
                modActionProactive           TruthValue,
                modActionProactiveDetect     TruthValue,
                modActionCustomerActionable  TruthValue,
                modActionComplete            TruthValue}

modActionIndex OBJECT-TYPE
    SYNTAX      INTEGER
    ACCESS      read-only
    STATUS      mandatory
    DESCRIPTION "A unique number for each action in the module actions table."
    ::= {modActionEntry 1}

modActionDesc OBJECT-TYPE
    SYNTAX      DisplayString
    ACCESS      read-only
    STATUS      mandatory
    DESCRIPTION "A description of the module action."
    ::= {modActionEntry 2}

modActionType OBJECT-TYPE
    SYNTAX      ActionType
    ACCESS      read-only
    STATUS      mandatory
    DESCRIPTION "An enumerated value indicating the type of action performed on
                 the module."
    ::= {modActionEntry 3}

modActionFaultDetect OBJECT-TYPE
    SYNTAX      TruthValue
    ACCESS      read-only
    STATUS      mandatory
    DESCRIPTION "A value of TRUE means the module can automatically detect that
                 the action has been performed for the associated fault that
                 was reported."
    ::= {modActionEntry 4}

modActionProactive OBJECT-TYPE
    SYNTAX      TruthValue
    ACCESS      read-only
    STATUS      mandatory
    DESCRIPTION "A value of TRUE means the action can be performed on the
                 module before the associated fault occurs."
    ::= {modActionEntry 5}

modActionProactiveDetect OBJECT-TYPE
    SYNTAX      TruthValue
    ACCESS      read-only
    STATUS      mandatory
    DESCRIPTION "A value of TRUE means the module can, through its sensors,
                 automatically detect that the action has been performed before
                 the associated fault occurs."
    ::= {modActionEntry 6}

modActionCustomerActionable OBJECT-TYPE
    SYNTAX      TruthValue
    ACCESS      read-only
    STATUS      mandatory
    DESCRIPTION "A value of TRUE means the customer can perform the action."
    ::= {modActionEntry 7}

modActionComplete OBJECT-TYPE
    SYNTAX      TruthValue
    ACCESS      write-only
    STATUS      mandatory
    DESCRIPTION "Setting the value of this attribute to TRUE informs the module
                 that the action has been performed, and clears the appropriate
                 module variables."
    ::= {modActionEntry 8}

END

RPNT-01-USBTHERMAL-CAPTUREBIN-MIB DEFINITIONS ::= BEGIN

--
-- SST RPNT-01-USBTHERMAL MIB
--

IMPORTS
    enterprises, Counter
        FROM RFC1155-SMI
    OBJECT-TYPE
        FROM RFC-1212
    DisplayString
        FROM RFC1213-MIB
    TruthValue
        FROM RFC1253-MIB
    sstDevice, VerificationState, ModuleState, VariableType, ActionType
        FROM NCR-CORESST-MIB;

    rpnt-01-UsbThermal    OBJECT IDENTIFIER ::= { sstDevice 138 }
    captureBin              OBJECT IDENTIFIER ::= { rpnt-01-UsbThermal 10 }

-------------------------------------------------------------------------------
-- SST Device Module - captureBin
-----------------------------------------------------------

modIdentifier OBJECT-TYPE
	SYNTAX INTEGER
   ACCESS read-only
   STATUS mandatory
   DESCRIPTION
   "Within the device, this is a unique identifier for the module."
   ::= { captureBin 1 }

modDesc OBJECT-TYPE
   SYNTAX DisplayString
   ACCESS read-only
   STATUS mandatory
   DESCRIPTION
   "A description of the module."
   ::= { captureBin 2 }

modReplenishable OBJECT-TYPE
   SYNTAX TruthValue
   ACCESS read-only
   STATUS mandatory
   DESCRIPTION
   "A value of TRUE means the module can be replenished (filled, emptied or renewed).
     A value of FALSE means it can be repaired or replaced."
   ::= { captureBin 3 }

modCurrentSummaryState OBJECT-TYPE
   SYNTAX ModuleState
   ACCESS read-only
   STATUS mandatory
   DESCRIPTION
   "The current summary state of the module."
   ::= { captureBin 4 }

modCurrentDetailedState OBJECT-TYPE
   SYNTAX INTEGER
   ACCESS read-only
   STATUS mandatory
   DESCRIPTION
   "The status code for the current detailed state."
   ::= { captureBin 5 }

modCurrentDetailedStateDesc OBJECT-TYPE
   SYNTAX DisplayString
   ACCESS read-only
   STATUS mandatory
   DESCRIPTION
   "A description of the current detailed state."
   ::= { captureBin 6 }

modPreviousSummaryState OBJECT-TYPE
   SYNTAX ModuleState
   ACCESS read-only
   STATUS mandatory
   DESCRIPTION
   "The previous summary state of the module."
   ::= { captureBin 7 }

modPreviousDetailedState OBJECT-TYPE
   SYNTAX INTEGER
   ACCESS read-only
   STATUS mandatory
   DESCRIPTION
   "The status code for the previous detailed state."
   ::= { captureBin 8 }

modPreviousDetailedStateDesc OBJECT-TYPE
   SYNTAX DisplayString
   ACCESS read-only
   STATUS mandatory
   DESCRIPTION
   "A description of the previous detailed state."
   ::= { captureBin 9 }

modFaultId OBJECT-TYPE
   SYNTAX DisplayString
   ACCESS read-only
   STATUS mandatory
   DESCRIPTION
   "A string of digits summarizing all the information about the current state of the module."
   ::= { captureBin 10 }

modAssemSerial OBJECT-TYPE
   SYNTAX DisplayString
   ACCESS read-write
   STATUS optional
   DESCRIPTION
   "The serial number of the module."
   ::= { captureBin 11 }

modAssemAssem OBJECT-TYPE
   SYNTAX DisplayString
   ACCESS read-write
   STATUS optional
   DESCRIPTION
   "The assembly number of the module."
   ::= { captureBin 12 }

modAssemCode OBJECT-TYPE
   SYNTAX DisplayString
   ACCESS read-write
   STATUS optional
   DESCRIPTION
   "The manufacturing code of the module."
   ::= { captureBin 13 }

modPMDate OBJECT-TYPE
   SYNTAX DisplayString
   ACCESS read-write
   STATUS optional
   DESCRIPTION
   "Date of the last scheduled service of the module."
   ::= { captureBin 14 }

modPMData OBJECT-TYPE
   SYNTAX OCTET STRING
   ACCESS read-write
   STATUS optional
   DESCRIPTION
   "Details of the last scheduled service of the module."
   ::= { captureBin 15 }

-----------------------------------------------------------
-- Device Module Variable Table - captureBin
-----------------------------------------------------------

modVarTable OBJECT-TYPE
   SYNTAX  SEQUENCE OF ModVarEntry
   ACCESS  not-accessible
   STATUS  mandatory
   DESCRIPTION
   "This group defines the attributes of the variables used by the module to manage its operational state."
   ::= { captureBin 16 }

modVarEntry OBJECT-TYPE
    SYNTAX      ModVarEntry
    ACCESS      not-accessible
    STATUS      mandatory
    DESCRIPTION "This defines the contents of the table."
    INDEX      {modVarIndex}
    ::= {modVarTable 1}

ModVarEntry ::=
    SEQUENCE   {modVarIndex         INTEGER,
                modVarDesc          DisplayString,
                modVarType          VariableType,
                modVarValue         Counter,
                modVarThreshold1    INTEGER,
                modVarThreshold2    INTEGER}

modVarIndex OBJECT-TYPE
    SYNTAX      INTEGER
    ACCESS      read-only
    STATUS      mandatory
    DESCRIPTION "This is a unique number for every entry in the module 
                 variables table."
    ::= {modVarEntry 1}

modVarDesc OBJECT-TYPE
    SYNTAX      DisplayString
    ACCESS      read-only
    STATUS      mandatory
    DESCRIPTION "A description of the module variable."
    ::= {modVarEntry 2}

modVarType OBJECT-TYPE
    SYNTAX      VariableType
    ACCESS      read-only
    STATUS      mandatory
    DESCRIPTION "An enumerated value indicating whether the variable has
                 thresholds and the type of threshold."
    ::= {modVarEntry 3}

modVarValue OBJECT-TYPE
    SYNTAX      Counter
    ACCESS      read-only
    STATUS      mandatory
    DESCRIPTION "The value of the module variable."
    ::= {modVarEntry 4}

modVarThreshold1 OBJECT-TYPE
    SYNTAX      INTEGER
    ACCESS      read-write
    STATUS      optional
    DESCRIPTION "For variables with one threshold, this is a final value.
                 For variables with two thresholds, this is a warning value."
    ::= {modVarEntry 5}

modVarThreshold2 OBJECT-TYPE
    SYNTAX      INTEGER
    ACCESS      read-write
    STATUS      optional
    DESCRIPTION "For variables with two thresholds, this is the final value."
    ::= {modVarEntry 6}

-------------------------------------------------------------------------------
-- Device Module Actions Table - captureBin
-----------------------------------------------------------

modActionTable OBJECT-TYPE
   SYNTAX  SEQUENCE OF ModActionEntry
   ACCESS  not-accessible
   STATUS  mandatory
   DESCRIPTION
   "This group defines the attributes of the actions that can be performed on the module to restore or maintain its normal operational state."
   ::= { captureBin 17 }

modActionEntry OBJECT-TYPE
    SYNTAX      ModActionEntry
    ACCESS      not-accessible
    STATUS      mandatory
    DESCRIPTION "This defines the contents of the table."
    INDEX      {modActionIndex}
    ::= {modActionTable 1}

ModActionEntry ::=
    SEQUENCE   {modActionIndex               INTEGER,
                modActionDesc                DisplayString,
                modActionType                ActionType,
                modActionFaultDetect         TruthValue,
                modActionProactive           TruthValue,
                modActionProactiveDetect     TruthValue,
                modActionCustomerActionable  TruthValue,
                modActionComplete            TruthValue}

modActionIndex OBJECT-TYPE
    SYNTAX      INTEGER
    ACCESS      read-only
    STATUS      mandatory
    DESCRIPTION "A unique number for each action in the module actions table."
    ::= {modActionEntry 1}

modActionDesc OBJECT-TYPE
    SYNTAX      DisplayString
    ACCESS      read-only
    STATUS      mandatory
    DESCRIPTION "A description of the module action."
    ::= {modActionEntry 2}

modActionType OBJECT-TYPE
    SYNTAX      ActionType
    ACCESS      read-only
    STATUS      mandatory
    DESCRIPTION "An enumerated value indicating the type of action performed on
                 the module."
    ::= {modActionEntry 3}

modActionFaultDetect OBJECT-TYPE
    SYNTAX      TruthValue
    ACCESS      read-only
    STATUS      mandatory
    DESCRIPTION "A value of TRUE means the module can automatically detect that
                 the action has been performed for the associated fault that
                 was reported."
    ::= {modActionEntry 4}

modActionProactive OBJECT-TYPE
    SYNTAX      TruthValue
    ACCESS      read-only
    STATUS      mandatory
    DESCRIPTION "A value of TRUE means the action can be performed on the
                 module before the associated fault occurs."
    ::= {modActionEntry 5}

modActionProactiveDetect OBJECT-TYPE
    SYNTAX      TruthValue
    ACCESS      read-only
    STATUS      mandatory
    DESCRIPTION "A value of TRUE means the module can, through its sensors,
                 automatically detect that the action has been performed before
                 the associated fault occurs."
    ::= {modActionEntry 6}

modActionCustomerActionable OBJECT-TYPE
    SYNTAX      TruthValue
    ACCESS      read-only
    STATUS      mandatory
    DESCRIPTION "A value of TRUE means the customer can perform the action."
    ::= {modActionEntry 7}

modActionComplete OBJECT-TYPE
    SYNTAX      TruthValue
    ACCESS      write-only
    STATUS      mandatory
    DESCRIPTION "Setting the value of this attribute to TRUE informs the module
                 that the action has been performed, and clears the appropriate
                 module variables."
    ::= {modActionEntry 8}

END

RPNT-01-USBTHERMAL-PAPER-MIB DEFINITIONS ::= BEGIN

--
-- SST RPNT-01-USBTHERMAL MIB
--

IMPORTS
    enterprises, Counter
        FROM RFC1155-SMI
    OBJECT-TYPE
        FROM RFC-1212
    DisplayString
        FROM RFC1213-MIB
    TruthValue
        FROM RFC1253-MIB
    sstDevice, VerificationState, ModuleState, VariableType, ActionType
        FROM NCR-CORESST-MIB;

    rpnt-01-UsbThermal    OBJECT IDENTIFIER ::= { sstDevice 138 }
    paper              OBJECT IDENTIFIER ::= { rpnt-01-UsbThermal 11 }

-------------------------------------------------------------------------------
-- SST Device Module - paper
-----------------------------------------------------------

modIdentifier OBJECT-TYPE
	SYNTAX INTEGER
   ACCESS read-only
   STATUS mandatory
   DESCRIPTION
   "Within the device, this is a unique identifier for the module."
   ::= { paper 1 }

modDesc OBJECT-TYPE
   SYNTAX DisplayString
   ACCESS read-only
   STATUS mandatory
   DESCRIPTION
   "A description of the module."
   ::= { paper 2 }

modReplenishable OBJECT-TYPE
   SYNTAX TruthValue
   ACCESS read-only
   STATUS mandatory
   DESCRIPTION
   "A value of TRUE means the module can be replenished (filled, emptied or renewed).
     A value of FALSE means it can be repaired or replaced."
   ::= { paper 3 }

modCurrentSummaryState OBJECT-TYPE
   SYNTAX ModuleState
   ACCESS read-only
   STATUS mandatory
   DESCRIPTION
   "The current summary state of the module."
   ::= { paper 4 }

modCurrentDetailedState OBJECT-TYPE
   SYNTAX INTEGER
   ACCESS read-only
   STATUS mandatory
   DESCRIPTION
   "The status code for the current detailed state."
   ::= { paper 5 }

modCurrentDetailedStateDesc OBJECT-TYPE
   SYNTAX DisplayString
   ACCESS read-only
   STATUS mandatory
   DESCRIPTION
   "A description of the current detailed state."
   ::= { paper 6 }

modPreviousSummaryState OBJECT-TYPE
   SYNTAX ModuleState
   ACCESS read-only
   STATUS mandatory
   DESCRIPTION
   "The previous summary state of the module."
   ::= { paper 7 }

modPreviousDetailedState OBJECT-TYPE
   SYNTAX INTEGER
   ACCESS read-only
   STATUS mandatory
   DESCRIPTION
   "The status code for the previous detailed state."
   ::= { paper 8 }

modPreviousDetailedStateDesc OBJECT-TYPE
   SYNTAX DisplayString
   ACCESS read-only
   STATUS mandatory
   DESCRIPTION
   "A description of the previous detailed state."
   ::= { paper 9 }

modFaultId OBJECT-TYPE
   SYNTAX DisplayString
   ACCESS read-only
   STATUS mandatory
   DESCRIPTION
   "A string of digits summarizing all the information about the current state of the module."
   ::= { paper 10 }

modAssemSerial OBJECT-TYPE
   SYNTAX DisplayString
   ACCESS read-write
   STATUS optional
   DESCRIPTION
   "The serial number of the module."
   ::= { paper 11 }

modAssemAssem OBJECT-TYPE
   SYNTAX DisplayString
   ACCESS read-write
   STATUS optional
   DESCRIPTION
   "The assembly number of the module."
   ::= { paper 12 }

modAssemCode OBJECT-TYPE
   SYNTAX DisplayString
   ACCESS read-write
   STATUS optional
   DESCRIPTION
   "The manufacturing code of the module."
   ::= { paper 13 }

modPMDate OBJECT-TYPE
   SYNTAX DisplayString
   ACCESS read-write
   STATUS optional
   DESCRIPTION
   "Date of the last scheduled service of the module."
   ::= { paper 14 }

modPMData OBJECT-TYPE
   SYNTAX OCTET STRING
   ACCESS read-write
   STATUS optional
   DESCRIPTION
   "Details of the last scheduled service of the module."
   ::= { paper 15 }

-----------------------------------------------------------
-- Device Module Variable Table - paper
-----------------------------------------------------------

modVarTable OBJECT-TYPE
   SYNTAX  SEQUENCE OF ModVarEntry
   ACCESS  not-accessible
   STATUS  mandatory
   DESCRIPTION
   "This group defines the attributes of the variables used by the module to manage its operational state."
   ::= { paper 16 }

modVarEntry OBJECT-TYPE
    SYNTAX      ModVarEntry
    ACCESS      not-accessible
    STATUS      mandatory
    DESCRIPTION "This defines the contents of the table."
    INDEX      {modVarIndex}
    ::= {modVarTable 1}

ModVarEntry ::=
    SEQUENCE   {modVarIndex         INTEGER,
                modVarDesc          DisplayString,
                modVarType          VariableType,
                modVarValue         Counter,
                modVarThreshold1    INTEGER,
                modVarThreshold2    INTEGER}

modVarIndex OBJECT-TYPE
    SYNTAX      INTEGER
    ACCESS      read-only
    STATUS      mandatory
    DESCRIPTION "This is a unique number for every entry in the module 
                 variables table."
    ::= {modVarEntry 1}

modVarDesc OBJECT-TYPE
    SYNTAX      DisplayString
    ACCESS      read-only
    STATUS      mandatory
    DESCRIPTION "A description of the module variable."
    ::= {modVarEntry 2}

modVarType OBJECT-TYPE
    SYNTAX      VariableType
    ACCESS      read-only
    STATUS      mandatory
    DESCRIPTION "An enumerated value indicating whether the variable has
                 thresholds and the type of threshold."
    ::= {modVarEntry 3}

modVarValue OBJECT-TYPE
    SYNTAX      Counter
    ACCESS      read-only
    STATUS      mandatory
    DESCRIPTION "The value of the module variable."
    ::= {modVarEntry 4}

modVarThreshold1 OBJECT-TYPE
    SYNTAX      INTEGER
    ACCESS      read-write
    STATUS      optional
    DESCRIPTION "For variables with one threshold, this is a final value.
                 For variables with two thresholds, this is a warning value."
    ::= {modVarEntry 5}

modVarThreshold2 OBJECT-TYPE
    SYNTAX      INTEGER
    ACCESS      read-write
    STATUS      optional
    DESCRIPTION "For variables with two thresholds, this is the final value."
    ::= {modVarEntry 6}

-------------------------------------------------------------------------------
-- Device Module Actions Table - paper
-----------------------------------------------------------

modActionTable OBJECT-TYPE
   SYNTAX  SEQUENCE OF ModActionEntry
   ACCESS  not-accessible
   STATUS  mandatory
   DESCRIPTION
   "This group defines the attributes of the actions that can be performed on the module to restore or maintain its normal operational state."
   ::= { paper 17 }

modActionEntry OBJECT-TYPE
    SYNTAX      ModActionEntry
    ACCESS      not-accessible
    STATUS      mandatory
    DESCRIPTION "This defines the contents of the table."
    INDEX      {modActionIndex}
    ::= {modActionTable 1}

ModActionEntry ::=
    SEQUENCE   {modActionIndex               INTEGER,
                modActionDesc                DisplayString,
                modActionType                ActionType,
                modActionFaultDetect         TruthValue,
                modActionProactive           TruthValue,
                modActionProactiveDetect     TruthValue,
                modActionCustomerActionable  TruthValue,
                modActionComplete            TruthValue}

modActionIndex OBJECT-TYPE
    SYNTAX      INTEGER
    ACCESS      read-only
    STATUS      mandatory
    DESCRIPTION "A unique number for each action in the module actions table."
    ::= {modActionEntry 1}

modActionDesc OBJECT-TYPE
    SYNTAX      DisplayString
    ACCESS      read-only
    STATUS      mandatory
    DESCRIPTION "A description of the module action."
    ::= {modActionEntry 2}

modActionType OBJECT-TYPE
    SYNTAX      ActionType
    ACCESS      read-only
    STATUS      mandatory
    DESCRIPTION "An enumerated value indicating the type of action performed on
                 the module."
    ::= {modActionEntry 3}

modActionFaultDetect OBJECT-TYPE
    SYNTAX      TruthValue
    ACCESS      read-only
    STATUS      mandatory
    DESCRIPTION "A value of TRUE means the module can automatically detect that
                 the action has been performed for the associated fault that
                 was reported."
    ::= {modActionEntry 4}

modActionProactive OBJECT-TYPE
    SYNTAX      TruthValue
    ACCESS      read-only
    STATUS      mandatory
    DESCRIPTION "A value of TRUE means the action can be performed on the
                 module before the associated fault occurs."
    ::= {modActionEntry 5}

modActionProactiveDetect OBJECT-TYPE
    SYNTAX      TruthValue
    ACCESS      read-only
    STATUS      mandatory
    DESCRIPTION "A value of TRUE means the module can, through its sensors,
                 automatically detect that the action has been performed before
                 the associated fault occurs."
    ::= {modActionEntry 6}

modActionCustomerActionable OBJECT-TYPE
    SYNTAX      TruthValue
    ACCESS      read-only
    STATUS      mandatory
    DESCRIPTION "A value of TRUE means the customer can perform the action."
    ::= {modActionEntry 7}

modActionComplete OBJECT-TYPE
    SYNTAX      TruthValue
    ACCESS      write-only
    STATUS      mandatory
    DESCRIPTION "Setting the value of this attribute to TRUE informs the module
                 that the action has been performed, and clears the appropriate
                 module variables."
    ::= {modActionEntry 8}

END

RPNT-01-USBTHERMAL-DUALFEEDMECHANISM-MIB DEFINITIONS ::= BEGIN

--
-- SST RPNT-01-USBTHERMAL MIB
--

IMPORTS
    enterprises, Counter
        FROM RFC1155-SMI
    OBJECT-TYPE
        FROM RFC-1212
    DisplayString
        FROM RFC1213-MIB
    TruthValue
        FROM RFC1253-MIB
    sstDevice, VerificationState, ModuleState, VariableType, ActionType
        FROM NCR-CORESST-MIB;

    rpnt-01-UsbThermal    OBJECT IDENTIFIER ::= { sstDevice 138 }
    dualFeedMechanism              OBJECT IDENTIFIER ::= { rpnt-01-UsbThermal 16 }

-------------------------------------------------------------------------------
-- SST Device Module - dualFeedMechanism
-----------------------------------------------------------

modIdentifier OBJECT-TYPE
	SYNTAX INTEGER
   ACCESS read-only
   STATUS mandatory
   DESCRIPTION
   "Within the device, this is a unique identifier for the module."
   ::= { dualFeedMechanism 1 }

modDesc OBJECT-TYPE
   SYNTAX DisplayString
   ACCESS read-only
   STATUS mandatory
   DESCRIPTION
   "A description of the module."
   ::= { dualFeedMechanism 2 }

modReplenishable OBJECT-TYPE
   SYNTAX TruthValue
   ACCESS read-only
   STATUS mandatory
   DESCRIPTION
   "A value of TRUE means the module can be replenished (filled, emptied or renewed).
     A value of FALSE means it can be repaired or replaced."
   ::= { dualFeedMechanism 3 }

modCurrentSummaryState OBJECT-TYPE
   SYNTAX ModuleState
   ACCESS read-only
   STATUS mandatory
   DESCRIPTION
   "The current summary state of the module."
   ::= { dualFeedMechanism 4 }

modCurrentDetailedState OBJECT-TYPE
   SYNTAX INTEGER
   ACCESS read-only
   STATUS mandatory
   DESCRIPTION
   "The status code for the current detailed state."
   ::= { dualFeedMechanism 5 }

modCurrentDetailedStateDesc OBJECT-TYPE
   SYNTAX DisplayString
   ACCESS read-only
   STATUS mandatory
   DESCRIPTION
   "A description of the current detailed state."
   ::= { dualFeedMechanism 6 }

modPreviousSummaryState OBJECT-TYPE
   SYNTAX ModuleState
   ACCESS read-only
   STATUS mandatory
   DESCRIPTION
   "The previous summary state of the module."
   ::= { dualFeedMechanism 7 }

modPreviousDetailedState OBJECT-TYPE
   SYNTAX INTEGER
   ACCESS read-only
   STATUS mandatory
   DESCRIPTION
   "The status code for the previous detailed state."
   ::= { dualFeedMechanism 8 }

modPreviousDetailedStateDesc OBJECT-TYPE
   SYNTAX DisplayString
   ACCESS read-only
   STATUS mandatory
   DESCRIPTION
   "A description of the previous detailed state."
   ::= { dualFeedMechanism 9 }

modFaultId OBJECT-TYPE
   SYNTAX DisplayString
   ACCESS read-only
   STATUS mandatory
   DESCRIPTION
   "A string of digits summarizing all the information about the current state of the module."
   ::= { dualFeedMechanism 10 }

modAssemSerial OBJECT-TYPE
   SYNTAX DisplayString
   ACCESS read-write
   STATUS optional
   DESCRIPTION
   "The serial number of the module."
   ::= { dualFeedMechanism 11 }

modAssemAssem OBJECT-TYPE
   SYNTAX DisplayString
   ACCESS read-write
   STATUS optional
   DESCRIPTION
   "The assembly number of the module."
   ::= { dualFeedMechanism 12 }

modAssemCode OBJECT-TYPE
   SYNTAX DisplayString
   ACCESS read-write
   STATUS optional
   DESCRIPTION
   "The manufacturing code of the module."
   ::= { dualFeedMechanism 13 }

modPMDate OBJECT-TYPE
   SYNTAX DisplayString
   ACCESS read-write
   STATUS optional
   DESCRIPTION
   "Date of the last scheduled service of the module."
   ::= { dualFeedMechanism 14 }

modPMData OBJECT-TYPE
   SYNTAX OCTET STRING
   ACCESS read-write
   STATUS optional
   DESCRIPTION
   "Details of the last scheduled service of the module."
   ::= { dualFeedMechanism 15 }

-----------------------------------------------------------
-- Device Module Variable Table - dualFeedMechanism
-----------------------------------------------------------

modVarTable OBJECT-TYPE
   SYNTAX  SEQUENCE OF ModVarEntry
   ACCESS  not-accessible
   STATUS  mandatory
   DESCRIPTION
   "This group defines the attributes of the variables used by the module to manage its operational state."
   ::= { dualFeedMechanism 16 }

modVarEntry OBJECT-TYPE
    SYNTAX      ModVarEntry
    ACCESS      not-accessible
    STATUS      mandatory
    DESCRIPTION "This defines the contents of the table."
    INDEX      {modVarIndex}
    ::= {modVarTable 1}

ModVarEntry ::=
    SEQUENCE   {modVarIndex         INTEGER,
                modVarDesc          DisplayString,
                modVarType          VariableType,
                modVarValue         Counter,
                modVarThreshold1    INTEGER,
                modVarThreshold2    INTEGER}

modVarIndex OBJECT-TYPE
    SYNTAX      INTEGER
    ACCESS      read-only
    STATUS      mandatory
    DESCRIPTION "This is a unique number for every entry in the module 
                 variables table."
    ::= {modVarEntry 1}

modVarDesc OBJECT-TYPE
    SYNTAX      DisplayString
    ACCESS      read-only
    STATUS      mandatory
    DESCRIPTION "A description of the module variable."
    ::= {modVarEntry 2}

modVarType OBJECT-TYPE
    SYNTAX      VariableType
    ACCESS      read-only
    STATUS      mandatory
    DESCRIPTION "An enumerated value indicating whether the variable has
                 thresholds and the type of threshold."
    ::= {modVarEntry 3}

modVarValue OBJECT-TYPE
    SYNTAX      Counter
    ACCESS      read-only
    STATUS      mandatory
    DESCRIPTION "The value of the module variable."
    ::= {modVarEntry 4}

modVarThreshold1 OBJECT-TYPE
    SYNTAX      INTEGER
    ACCESS      read-write
    STATUS      optional
    DESCRIPTION "For variables with one threshold, this is a final value.
                 For variables with two thresholds, this is a warning value."
    ::= {modVarEntry 5}

modVarThreshold2 OBJECT-TYPE
    SYNTAX      INTEGER
    ACCESS      read-write
    STATUS      optional
    DESCRIPTION "For variables with two thresholds, this is the final value."
    ::= {modVarEntry 6}

-------------------------------------------------------------------------------
-- Device Module Actions Table - dualFeedMechanism
-----------------------------------------------------------

modActionTable OBJECT-TYPE
   SYNTAX  SEQUENCE OF ModActionEntry
   ACCESS  not-accessible
   STATUS  mandatory
   DESCRIPTION
   "This group defines the attributes of the actions that can be performed on the module to restore or maintain its normal operational state."
   ::= { dualFeedMechanism 17 }

modActionEntry OBJECT-TYPE
    SYNTAX      ModActionEntry
    ACCESS      not-accessible
    STATUS      mandatory
    DESCRIPTION "This defines the contents of the table."
    INDEX      {modActionIndex}
    ::= {modActionTable 1}

ModActionEntry ::=
    SEQUENCE   {modActionIndex               INTEGER,
                modActionDesc                DisplayString,
                modActionType                ActionType,
                modActionFaultDetect         TruthValue,
                modActionProactive           TruthValue,
                modActionProactiveDetect     TruthValue,
                modActionCustomerActionable  TruthValue,
                modActionComplete            TruthValue}

modActionIndex OBJECT-TYPE
    SYNTAX      INTEGER
    ACCESS      read-only
    STATUS      mandatory
    DESCRIPTION "A unique number for each action in the module actions table."
    ::= {modActionEntry 1}

modActionDesc OBJECT-TYPE
    SYNTAX      DisplayString
    ACCESS      read-only
    STATUS      mandatory
    DESCRIPTION "A description of the module action."
    ::= {modActionEntry 2}

modActionType OBJECT-TYPE
    SYNTAX      ActionType
    ACCESS      read-only
    STATUS      mandatory
    DESCRIPTION "An enumerated value indicating the type of action performed on
                 the module."
    ::= {modActionEntry 3}

modActionFaultDetect OBJECT-TYPE
    SYNTAX      TruthValue
    ACCESS      read-only
    STATUS      mandatory
    DESCRIPTION "A value of TRUE means the module can automatically detect that
                 the action has been performed for the associated fault that
                 was reported."
    ::= {modActionEntry 4}

modActionProactive OBJECT-TYPE
    SYNTAX      TruthValue
    ACCESS      read-only
    STATUS      mandatory
    DESCRIPTION "A value of TRUE means the action can be performed on the
                 module before the associated fault occurs."
    ::= {modActionEntry 5}

modActionProactiveDetect OBJECT-TYPE
    SYNTAX      TruthValue
    ACCESS      read-only
    STATUS      mandatory
    DESCRIPTION "A value of TRUE means the module can, through its sensors,
                 automatically detect that the action has been performed before
                 the associated fault occurs."
    ::= {modActionEntry 6}

modActionCustomerActionable OBJECT-TYPE
    SYNTAX      TruthValue
    ACCESS      read-only
    STATUS      mandatory
    DESCRIPTION "A value of TRUE means the customer can perform the action."
    ::= {modActionEntry 7}

modActionComplete OBJECT-TYPE
    SYNTAX      TruthValue
    ACCESS      write-only
    STATUS      mandatory
    DESCRIPTION "Setting the value of this attribute to TRUE informs the module
                 that the action has been performed, and clears the appropriate
                 module variables."
    ::= {modActionEntry 8}

END

RPNT-01-USBTHERMAL-DUALFEEDPAPER-MIB DEFINITIONS ::= BEGIN

--
-- SST RPNT-01-USBTHERMAL MIB
--

IMPORTS
    enterprises, Counter
        FROM RFC1155-SMI
    OBJECT-TYPE
        FROM RFC-1212
    DisplayString
        FROM RFC1213-MIB
    TruthValue
        FROM RFC1253-MIB
    sstDevice, VerificationState, ModuleState, VariableType, ActionType
        FROM NCR-CORESST-MIB;

    rpnt-01-UsbThermal    OBJECT IDENTIFIER ::= { sstDevice 138 }
    dualFeedPaper              OBJECT IDENTIFIER ::= { rpnt-01-UsbThermal 17 }

-------------------------------------------------------------------------------
-- SST Device Module - dualFeedPaper
-----------------------------------------------------------

modIdentifier OBJECT-TYPE
	SYNTAX INTEGER
   ACCESS read-only
   STATUS mandatory
   DESCRIPTION
   "Within the device, this is a unique identifier for the module."
   ::= { dualFeedPaper 1 }

modDesc OBJECT-TYPE
   SYNTAX DisplayString
   ACCESS read-only
   STATUS mandatory
   DESCRIPTION
   "A description of the module."
   ::= { dualFeedPaper 2 }

modReplenishable OBJECT-TYPE
   SYNTAX TruthValue
   ACCESS read-only
   STATUS mandatory
   DESCRIPTION
   "A value of TRUE means the module can be replenished (filled, emptied or renewed).
     A value of FALSE means it can be repaired or replaced."
   ::= { dualFeedPaper 3 }

modCurrentSummaryState OBJECT-TYPE
   SYNTAX ModuleState
   ACCESS read-only
   STATUS mandatory
   DESCRIPTION
   "The current summary state of the module."
   ::= { dualFeedPaper 4 }

modCurrentDetailedState OBJECT-TYPE
   SYNTAX INTEGER
   ACCESS read-only
   STATUS mandatory
   DESCRIPTION
   "The status code for the current detailed state."
   ::= { dualFeedPaper 5 }

modCurrentDetailedStateDesc OBJECT-TYPE
   SYNTAX DisplayString
   ACCESS read-only
   STATUS mandatory
   DESCRIPTION
   "A description of the current detailed state."
   ::= { dualFeedPaper 6 }

modPreviousSummaryState OBJECT-TYPE
   SYNTAX ModuleState
   ACCESS read-only
   STATUS mandatory
   DESCRIPTION
   "The previous summary state of the module."
   ::= { dualFeedPaper 7 }

modPreviousDetailedState OBJECT-TYPE
   SYNTAX INTEGER
   ACCESS read-only
   STATUS mandatory
   DESCRIPTION
   "The status code for the previous detailed state."
   ::= { dualFeedPaper 8 }

modPreviousDetailedStateDesc OBJECT-TYPE
   SYNTAX DisplayString
   ACCESS read-only
   STATUS mandatory
   DESCRIPTION
   "A description of the previous detailed state."
   ::= { dualFeedPaper 9 }

modFaultId OBJECT-TYPE
   SYNTAX DisplayString
   ACCESS read-only
   STATUS mandatory
   DESCRIPTION
   "A string of digits summarizing all the information about the current state of the module."
   ::= { dualFeedPaper 10 }

modAssemSerial OBJECT-TYPE
   SYNTAX DisplayString
   ACCESS read-write
   STATUS optional
   DESCRIPTION
   "The serial number of the module."
   ::= { dualFeedPaper 11 }

modAssemAssem OBJECT-TYPE
   SYNTAX DisplayString
   ACCESS read-write
   STATUS optional
   DESCRIPTION
   "The assembly number of the module."
   ::= { dualFeedPaper 12 }

modAssemCode OBJECT-TYPE
   SYNTAX DisplayString
   ACCESS read-write
   STATUS optional
   DESCRIPTION
   "The manufacturing code of the module."
   ::= { dualFeedPaper 13 }

modPMDate OBJECT-TYPE
   SYNTAX DisplayString
   ACCESS read-write
   STATUS optional
   DESCRIPTION
   "Date of the last scheduled service of the module."
   ::= { dualFeedPaper 14 }

modPMData OBJECT-TYPE
   SYNTAX OCTET STRING
   ACCESS read-write
   STATUS optional
   DESCRIPTION
   "Details of the last scheduled service of the module."
   ::= { dualFeedPaper 15 }

-----------------------------------------------------------
-- Device Module Variable Table - dualFeedPaper
-----------------------------------------------------------

modVarTable OBJECT-TYPE
   SYNTAX  SEQUENCE OF ModVarEntry
   ACCESS  not-accessible
   STATUS  mandatory
   DESCRIPTION
   "This group defines the attributes of the variables used by the module to manage its operational state."
   ::= { dualFeedPaper 16 }

modVarEntry OBJECT-TYPE
    SYNTAX      ModVarEntry
    ACCESS      not-accessible
    STATUS      mandatory
    DESCRIPTION "This defines the contents of the table."
    INDEX      {modVarIndex}
    ::= {modVarTable 1}

ModVarEntry ::=
    SEQUENCE   {modVarIndex         INTEGER,
                modVarDesc          DisplayString,
                modVarType          VariableType,
                modVarValue         Counter,
                modVarThreshold1    INTEGER,
                modVarThreshold2    INTEGER}

modVarIndex OBJECT-TYPE
    SYNTAX      INTEGER
    ACCESS      read-only
    STATUS      mandatory
    DESCRIPTION "This is a unique number for every entry in the module 
                 variables table."
    ::= {modVarEntry 1}

modVarDesc OBJECT-TYPE
    SYNTAX      DisplayString
    ACCESS      read-only
    STATUS      mandatory
    DESCRIPTION "A description of the module variable."
    ::= {modVarEntry 2}

modVarType OBJECT-TYPE
    SYNTAX      VariableType
    ACCESS      read-only
    STATUS      mandatory
    DESCRIPTION "An enumerated value indicating whether the variable has
                 thresholds and the type of threshold."
    ::= {modVarEntry 3}

modVarValue OBJECT-TYPE
    SYNTAX      Counter
    ACCESS      read-only
    STATUS      mandatory
    DESCRIPTION "The value of the module variable."
    ::= {modVarEntry 4}

modVarThreshold1 OBJECT-TYPE
    SYNTAX      INTEGER
    ACCESS      read-write
    STATUS      optional
    DESCRIPTION "For variables with one threshold, this is a final value.
                 For variables with two thresholds, this is a warning value."
    ::= {modVarEntry 5}

modVarThreshold2 OBJECT-TYPE
    SYNTAX      INTEGER
    ACCESS      read-write
    STATUS      optional
    DESCRIPTION "For variables with two thresholds, this is the final value."
    ::= {modVarEntry 6}

-------------------------------------------------------------------------------
-- Device Module Actions Table - dualFeedPaper
-----------------------------------------------------------

modActionTable OBJECT-TYPE
   SYNTAX  SEQUENCE OF ModActionEntry
   ACCESS  not-accessible
   STATUS  mandatory
   DESCRIPTION
   "This group defines the attributes of the actions that can be performed on the module to restore or maintain its normal operational state."
   ::= { dualFeedPaper 17 }

modActionEntry OBJECT-TYPE
    SYNTAX      ModActionEntry
    ACCESS      not-accessible
    STATUS      mandatory
    DESCRIPTION "This defines the contents of the table."
    INDEX      {modActionIndex}
    ::= {modActionTable 1}

ModActionEntry ::=
    SEQUENCE   {modActionIndex               INTEGER,
                modActionDesc                DisplayString,
                modActionType                ActionType,
                modActionFaultDetect         TruthValue,
                modActionProactive           TruthValue,
                modActionProactiveDetect     TruthValue,
                modActionCustomerActionable  TruthValue,
                modActionComplete            TruthValue}

modActionIndex OBJECT-TYPE
    SYNTAX      INTEGER
    ACCESS      read-only
    STATUS      mandatory
    DESCRIPTION "A unique number for each action in the module actions table."
    ::= {modActionEntry 1}

modActionDesc OBJECT-TYPE
    SYNTAX      DisplayString
    ACCESS      read-only
    STATUS      mandatory
    DESCRIPTION "A description of the module action."
    ::= {modActionEntry 2}

modActionType OBJECT-TYPE
    SYNTAX      ActionType
    ACCESS      read-only
    STATUS      mandatory
    DESCRIPTION "An enumerated value indicating the type of action performed on
                 the module."
    ::= {modActionEntry 3}

modActionFaultDetect OBJECT-TYPE
    SYNTAX      TruthValue
    ACCESS      read-only
    STATUS      mandatory
    DESCRIPTION "A value of TRUE means the module can automatically detect that
                 the action has been performed for the associated fault that
                 was reported."
    ::= {modActionEntry 4}

modActionProactive OBJECT-TYPE
    SYNTAX      TruthValue
    ACCESS      read-only
    STATUS      mandatory
    DESCRIPTION "A value of TRUE means the action can be performed on the
                 module before the associated fault occurs."
    ::= {modActionEntry 5}

modActionProactiveDetect OBJECT-TYPE
    SYNTAX      TruthValue
    ACCESS      read-only
    STATUS      mandatory
    DESCRIPTION "A value of TRUE means the module can, through its sensors,
                 automatically detect that the action has been performed before
                 the associated fault occurs."
    ::= {modActionEntry 6}

modActionCustomerActionable OBJECT-TYPE
    SYNTAX      TruthValue
    ACCESS      read-only
    STATUS      mandatory
    DESCRIPTION "A value of TRUE means the customer can perform the action."
    ::= {modActionEntry 7}

modActionComplete OBJECT-TYPE
    SYNTAX      TruthValue
    ACCESS      write-only
    STATUS      mandatory
    DESCRIPTION "Setting the value of this attribute to TRUE informs the module
                 that the action has been performed, and clears the appropriate
                 module variables."
    ::= {modActionEntry 8}

END
